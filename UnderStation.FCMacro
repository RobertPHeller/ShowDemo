#*****************************************************************************
#
#  System        : 
#  Module        : 
#  Object Name   : $RCSfile$
#  Revision      : $Revision$
#  Date          : $Date$
#  Author        : $Author$
#  Created By    : Robert Heller
#  Created       : 2026-01-28 19:32:47
#  Last Modified : <260511.1405>
#
#  Description	
#
#  Notes
#
#  History
#	
#*****************************************************************************
#
#    Copyright (C) 2026  Robert Heller D/B/A Deepwoods Software
#			51 Locke Hill Road
#			Wendell, MA 01379-9728
#
#    This program is free software; you can redistribute it and/or modify
#    it under the terms of the GNU General Public License as published by
#    the Free Software Foundation; either version 2 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program; if not, write to the Free Software
#    Foundation, Inc., 675 Mass Ave, Cambridge, MA 02139, USA.
#
# 
#
#*****************************************************************************


import FreeCAD as App
import Part, TechDraw, Mesh
from FreeCAD import Base

import os
import sys
sys.path.append(os.path.dirname(__file__))
import csv
import math
import Units
from debug import debug

import LaserCut

def NormalizeMM(x):
    return round(x,3)

class BOMHelper(object):
    __BOM = dict()
    @classmethod
    def AddPiece(cls,width,height,kind):
        key = (NormalizeMM(width),NormalizeMM(height),kind)
        if key in cls.__BOM:
            cls.__BOM[key] += 1
        else:
            cls.__BOM[key] = 1
    @classmethod
    def _normPartSizeMM(cls,t):
        return ("%.3fx%.3f" % t)
    @staticmethod
    def _inch(mm):
        return mm / 25.4
    @classmethod
    def _normPartSizeIN(cls,t):
        X, Y = t
        return ("%.4fx%.4f" % (cls._inch(X), cls._inch(Y)))
    _units = 'in'
    @classmethod
    def SetUnits(cls,units):
        if units == 'in' or units == 'mm':
            cls._units = units
        else:
            raise RuntimeError("Unsupport units!")
    @classmethod
    def GetUnits(cls):
        return cls._units
    @classmethod
    def _normPartSize(cls,t):
        if cls._units == 'in':
            return cls._normPartSizeIN(t)
        elif cls._units == 'mm':
            return BOMHelper._normPartSizeMM(t)
        else:
            raise RuntimeError("Unsupport units!")
    @classmethod
    def ListCuts(cls,filename):
        keys = list(cls.__BOM.keys())
        keys.sort()
        f = open(filename,"w")
        w = csv.writer(f)
        w.writerow([("Size (%s)" % cls._units),"Kind","Count"])
        for key in keys:
            X, Y, kind = key
            w.writerow([cls._normPartSize((X,Y)),kind,cls.__BOM[key]])
        f.close()

class PartsHelper(object):
    __BOP = dict()
    @classmethod
    def AddPart(cls,part,count=1):
        if part in cls.__BOP:
            cls.__BOP[part] += count
        else:
            cls.__BOP[part] = count
    @classmethod
    def ListParts(cls,filename):
        parts = list(cls.__BOP.keys())
        parts.sort()
        f = open(filename,"w")
        w = csv.writer(f)
        w.writerow(["Part","Count"])
        for part in parts:
            w.writerow([ part, cls.__BOP[part] ])
        f.close()

class Elevator(object):
    __CabinWidth  = Units.HOScale(1600)
    __CabinLength = Units.HOScale(2100)
    ShaftWidth  = Units.HOScale(2200)
    ShaftLength = Units.HOScale(2800)
    __DoorWidth   = Units.HOScale(1000)
    __HeadRoom    = Units.HOScale(Units.mm(100))
    __Mechanical  = Units.HOScale(Units.mm(50))
    __ShaftColor  = tuple([0xaa/255.0,0xaa/255.0,0xaa/255.0])
    def __init__(self,name,origin,liftheight):
        self.name = name
        if not isinstance(origin,Base.Vector):
            raise RuntimeError("origin is not a Vector!")
        self.origin = origin
        self.shaft = Part.makePlane(self.ShaftWidth,
                                    self.ShaftLength,
                                    self.origin)\
           .extrude(Base.Vector(0,0,liftheight+\
                                    (self.__HeadRoom*1.2)+\
                                    self.__Mechanical))
    def show(self,doc=None):
        if doc==None:
            doc = App.activeDocument()
        obj = doc.addObject("Part::Feature",self.name+"_shaft")
        obj.Shape = self.shaft
        obj.Label=self.name+"_shaft"
        obj.ViewObject.ShapeColor=self.__ShaftColor

class UnderStation(BOMHelper, PartsHelper):
    # Walthers Cornerstone Part # 933-3175
    # Butterfly Style Station Platform Shelter 11 x 2-1/8 x 2-1/4"
    __ShortPlatformLength = Units.mm(11)
    # 2X end to end
    __LongPlatformLength  = Units.mm(22)
    __PlatformWidth       = Units.mm(2.125)
    __PlatformRoofHeight  = Units.mm(2.25)
    # Raised platform (level boarding)
    __PlatformHeight      = Units.mm(Units.HOScale(51))
    __CombinedTrackAndPlatformWidth = Units.mm(8.1)
    __MainWallWidth = .080*25.4
    __GlassWallWidth  = .040*25.4 
    __PlatformRoofThickness = .080*25.4
    # Total platform edge-to-edge + 
    #                Wall + 
    #                Street elevator shaft + 
    #                street stairs
    @property
    def __TotalStationDepth(self):
        return self.__CombinedTrackAndPlatformWidth +\
            self.__MainWallWidth+\
            Elevator.ShaftWidth +\
            Units.HOScale(Units.mm(Units.inches(14)))
    __TotalStationLength = Units.mm(22.5)
    __TotalStationHeight = Units.mm(Units.inches(Units.HOScale( 15 )))
    __StationUnderOffset = Units.mm(.25+1)
    __StairRiser         = Units.mm(Units.HOScale(5.5))
    __StairTread         = Units.mm(Units.HOScale(11))
    __CurbHeight         = Units.mm(Units.HOScale(6))
    __PostOffset         = Units.mm(Units.HOScale(Units.inches(5)))
    __PostSpacing        = Units.mm(Units.HOScale(Units.inches(10)))
    __PostDiameter       = Units.mm(Units.HOScale(Units.inches(2)))
    @property
    def __StairRiseRatio(self):
        return self.__StairTread/self.__StairRiser
    __StairLandingRiseMax = Units.mm(Units.inches(Units.HOScale( 12 )))
    __StairHeadRoomMin    = Units.mm(Units.HOScale(80))
    __PlatformStairWidth  = Units.mm(Units.inches(Units.HOScale( 6 )))
    @property
    def __PlatformStairLanding(self):
        return self.__StairHeadRoom
    __StreetStairWidth   = Units.mm(Units.inches(Units.HOScale( 12 )))
    @property
    def __StreetStairLanding(self):
        return self.__StreetStairWidth
    @property
    def __StreetStairTotalRise(self):
        return self.__TotalStationHeight + self.__StationUnderOffset + self.__CurbHeight
    @property
    def __PlatformStairTotalRise(self):
        return self.__TotalStationHeight + \
               self.__StationUnderOffset + \
               self.__PlatformHeight
    __StairsColor  = tuple([0xaa/255.0,0xaa/255.0,0xaa/255.0])
    __FloorColor   = (.5,.5,.5)
    def __TotalStairLength(self,height,landing):
        landings = math.floor(height / self.__StairLandingRiseMax)
        return (height*self.__StairRiseRatio)+(landings*landing)
    def __makeStairs(self,origin,height,width,extraLanding=0):
        z=0
        lastLanding = 0
        length=self.__TotalStairLength(height,width)+extraLanding
        
        x = 0
        stair = None
        while z < height and x < length:
            r = self.__StairRiser
            if z+r > height:
                r = height-z
            tread = self.__StairTread
            treadLength = length-x
            step = Part.makePlane(treadLength,width,origin.add(Base.Vector(x,0,z)))\
                    .extrude(Base.Vector(0,0,r))
            if stair == None:
                stair = step
            else:
                stair = stair.fuse(step)
            z = z+r
            if z >= lastLanding+self.__StairLandingRiseMax:
                x = x+ width
                lastLanding = z
            else:
                x = x+tread
        self.AddPart("Stairs_%.4fx%.4f"%(width,height))
        return stair
    def __makeStairsRev(self,origin,height,width,extraLanding=0):
        z=0
        lastLanding = 0
        length=self.__TotalStairLength(height,width)+extraLanding
        
        x = 0
        stair = None
        while z < height and x < length:
            r = self.__StairRiser
            if z+r > height:
                r = height-z
            tread = self.__StairTread
            treadLength = length-x
            step = Part.makePlane(treadLength,width,origin.add(Base.Vector(0,0,z)))\
                    .extrude(Base.Vector(0,0,r))
            if stair == None:
                stair = step
            else:
                stair = stair.fuse(step)
            z = z+r
            if z >= lastLanding+self.__StairLandingRiseMax:
                x = x+ width
                lastLanding = z
            else:
                x = x+tread
        self.AddPart("Stairs_%.4fx%.4f"%(width,height))
        return stair
    __DoorCutHeight = Units.mm(.98)
    __SingleDoorCutWidth = Units.mm(.46)
    __DoubleDoorCutWidth = Units.mm(.875)
    def __doubleDoorCutX(self,origin,DeltaX):
        doorCut = Part.makePlane(self.__DoorCutHeight,self.__DoubleDoorCutWidth,
                                 origin.add(
                                    Base.Vector(0,self.__DoubleDoorCutWidth,0)),
                                 Base.Vector(1,0,0)
               ).extrude(Base.Vector(DeltaX,0,0))
        self.door = doorCut
        return doorCut
    def __doubleDoorCutY(self,origin,DeltaY):
        doorCut = Part.makePlane(self.__DoorCutHeight,self.__DoubleDoorCutWidth,
                                 origin.add(
                                    Base.Vector(0,0,0)),
                                 Base.Vector(0,1,0)
               ).extrude(Base.Vector(0,DeltaY,0))
        return doorCut
    def __singleDoorCut(self,origin,DeltaX):
        doorCut = Part.makePlane(self.__DoorCutHeight,self.__SingleDoorCutWidth,
                                 origin.add(
                                    Base.Vector(0,self.__SingleDoorCutWidth,0)),
                                 Base.Vector(1,0,0)
               ).extrude(Base.Vector(DeltaX,0,0))
        #self.doorCut = doorCut
        return doorCut
    def __init__(self,name,origin):
        LaserCut.LaserCut.SetPrefix("UnderStation")
        self.name = name
        if not isinstance(origin,Base.Vector):
            raise RuntimeError("origin is not a Vector!")
        self.origin = origin
        self.streetElevator = Elevator(
            "StreetElevator",    
            self.origin.add(Base.Vector(self.__LongPlatformLength-
                                            self.__StreetStairWidth-
                                            Elevator.ShaftLength-
                                            9.85,
                            Units.mm(8.1)+self.__MainWallWidth,
                            -(self.__TotalStationHeight+self.__StationUnderOffset))),
            self.__TotalStationHeight+
                self.__StationUnderOffset+
                self.__CurbHeight)
        self.AddPart("StreetElevator")
        streetStairLen = self.__TotalStairLength(self.__StreetStairTotalRise,
                                                 self.__StreetStairWidth)
        #debug("*** UnderStation.__init__(): streetStairLen = %f",streetStairLen)
        self.streetStairOrigin = origin.add(Base.Vector(
                                          self.__TotalStationLength-\
                                          streetStairLen-\
                                          (2*Elevator.ShaftWidth),
                                          self.__TotalStationDepth-\
                                          self.__StreetStairWidth+\
                                          self.__MainWallWidth,
                                         -(self.__TotalStationHeight+self.__StationUnderOffset)))
        self.streetStair = self.__makeStairs(self.streetStairOrigin,
                                        self.__StreetStairTotalRise,
                                        self.__StreetStairWidth,
                                        Elevator.ShaftWidth)
        platformStairLen = self.__TotalStairLength(
                                    self.__PlatformStairTotalRise,
                                    self.__PlatformStairWidth)
        #debug("*** UnderStation.__init__(): platformStairLen = %f",platformStairLen)
        self.platform1StairOrigin = origin.add(Base.Vector(
                                                    self.__TotalStationLength-\
                                                        self.__ShortPlatformLength-\
                                                        self.__PlatformStairWidth,
                                                    self.__CombinedTrackAndPlatformWidth-\
                                                    self.__PlatformStairWidth,
                                                    -(self.__TotalStationHeight+self.__StationUnderOffset)))
        self.platform1Stair = self.__makeStairs(self.platform1StairOrigin,
                                       self.__PlatformStairTotalRise,
                                       self.__PlatformStairWidth)
        self.platform2StairOrigin = origin.add(Base.Vector(
                                                    self.__TotalStationLength-\
                                                        self.__ShortPlatformLength-\
                                                        self.__PlatformStairWidth,
                                                    0,
                                                    -(self.__TotalStationHeight+self.__StationUnderOffset)))
        self.platform2Stair = self.__makeStairs(self.platform2StairOrigin,
                                       self.__PlatformStairTotalRise,
                                       self.__PlatformStairWidth)
        self.stationFloor = Part.makePlane(self.__TotalStationLength+(2*self.__MainWallWidth),
                                           self.__TotalStationDepth+(2*self.__MainWallWidth),
                                           self.origin.add(Base.Vector(-self.__MainWallWidth,0,-(self.__TotalStationHeight+self.__StationUnderOffset))))\
                   .extrude(Base.Vector(0,0,-self.__MainWallWidth))
        bb = self.stationFloor.BoundBox
        self.AddPiece(bb.XLength,bb.YLength,".080 Styreen (SSS-10824)")
        LaserCut.StyreneSSS_10824Cut.AddCut(self.stationFloor)
        elevator1Origin = self.origin.add(Base.Vector(self.__ShortPlatformLength-(3*Elevator.ShaftLength),
                                        self.__CombinedTrackAndPlatformWidth-Elevator.ShaftLength,
                                        -(self.__TotalStationHeight+self.__StationUnderOffset)))
        self.platform1Elevator = Elevator(
            "Platform1Elevator",
            elevator1Origin,
            self.__PlatformStairTotalRise)
        self.AddPart("PlatformElevator")
        elevatorShelterOrigin = Base.Vector(elevator1Origin.x,
                                            elevator1Origin.y+Elevator.ShaftLength,
                                            origin.z+self.__PlatformHeight)
        elevatorShelter = Part.makePlane(self.__PlatformRoofHeight-self.__PlatformHeight,
                                         Elevator.ShaftLength,
                                         elevatorShelterOrigin.add(
                                            Base.Vector(
                                                Elevator.ShaftWidth+\
                                                self.__PlatformStairWidth,
                                                0,
                                                0)),
                                         Base.Vector(1,0,0))\
              .extrude(Base.Vector(-self.__GlassWallWidth,0,0))
        bb = elevatorShelter.BoundBox
        elevatorShelterDoorOrigin = Base.Vector(bb.XMin,
                                        bb.YMin+
                                            ((Elevator.ShaftLength-
                                              self.__SingleDoorCutWidth)/2),
                                        bb.ZMin)
        elevatorShelter = elevatorShelter.cut(
            self.__singleDoorCut(elevatorShelterDoorOrigin,
                                 self.__GlassWallWidth))
        self.AddPiece(bb.YLength,bb.ZLength,".040 Clear Copolyester (SSC-104)")
        LaserCut.CopolysterSSC_104Cut.AddCut(elevatorShelter)
        e1sA = Part.makePlane(self.__PlatformRoofHeight-self.__PlatformHeight,
                           self.__PlatformStairWidth,
                           elevatorShelterOrigin.add(
                            Base.Vector(
                                Elevator.ShaftWidth,
                                -Elevator.ShaftLength,
                                0)),
                           Base.Vector(0,1,0)).extrude(Base.Vector(0,self.__GlassWallWidth))
        self.elevator1Shelter = elevatorShelter.fuse(e1sA)
        bb = e1sA.BoundBox
        self.AddPiece(bb.XLength,bb.ZLength,".040 Clear Copolyester (SSC-104)")
        LaserCut.CopolysterSSC_104Cut.AddCut(e1sA)
        self.AddPart("Tichy Train Group #8195 Single Glass Door")
        postSkip1 = (elevator1Origin.x,elevator1Origin.x+Elevator.ShaftWidth+self.__PlatformStairWidth)
        elevator2Origin = self.origin.add(Base.Vector(self.__ShortPlatformLength-(3*Elevator.ShaftLength),
                                        0,
                                        -(self.__TotalStationHeight+self.__StationUnderOffset)))
        self.platform2Elevator = Elevator(
            "Platform2Elevator",
            elevator2Origin,
            self.__PlatformStairTotalRise)
        self.AddPart("PlatformElevator")
        elevatorShelterOrigin = Base.Vector(elevator2Origin.x,
                                            elevator2Origin.y+Elevator.ShaftLength,
                                            origin.z+self.__PlatformHeight)
        elevatorShelter = Part.makePlane(self.__PlatformRoofHeight-self.__PlatformHeight,
                                         Elevator.ShaftLength,
                                         elevatorShelterOrigin.add(
                                            Base.Vector(
                                                Elevator.ShaftWidth+\
                                                self.__PlatformStairWidth,
                                                0,
                                                0)),
                                         Base.Vector(1,0,0))\
              .extrude(Base.Vector(-self.__GlassWallWidth,0,0))
        bb = elevatorShelter.BoundBox
        elevatorShelterDoorOrigin = Base.Vector(bb.XMin,
                                        bb.YMin+
                                            ((Elevator.ShaftLength-
                                              self.__SingleDoorCutWidth)/2),
                                        bb.ZMin)
        elevatorShelter = elevatorShelter.cut(
            self.__singleDoorCut(elevatorShelterDoorOrigin,
                                 self.__GlassWallWidth))
        self.AddPiece(bb.YLength,bb.ZLength,".040 Clear Copolyester (SSC-104)")
        LaserCut.CopolysterSSC_104Cut.AddCut(elevatorShelter)
        e2sA = Part.makePlane(self.__PlatformRoofHeight-self.__PlatformHeight,
                           self.__PlatformStairWidth,
                           elevatorShelterOrigin.add(
                            Base.Vector(
                                Elevator.ShaftWidth,
                                0,
                                0)),
                           Base.Vector(0,1,0)).extrude(Base.Vector(0,-self.__GlassWallWidth))
        LaserCut.CopolysterSSC_104Cut.AddCut(e2sA)
        self.elevator2Shelter = elevatorShelter.fuse(e2sA)
        bb = e2sA.BoundBox
        self.AddPiece(bb.XLength,bb.ZLength,".040 Clear Copolyester (SSC-104)")
        self.AddPart("Tichy Train Group #8195 Single Glass Door")
        platformBaseHeight = self.__PlatformHeight-Units.mm(Units.HOScale(12))
        platformBaseExtrude = Base.Vector(0,0,platformBaseHeight)
        platformBaseWidth = self.__PlatformWidth-Units.mm(Units.HOScale(12))
        p1borigin = origin.add(Base.Vector(
                                        0,
                                        self.__CombinedTrackAndPlatformWidth-\
                                            self.__PlatformWidth+\
                                            Units.mm(Units.HOScale(12)),
                                        0))
        platform = Part.makePlane(self.__LongPlatformLength,
                                  platformBaseWidth,
                                  p1borigin)\
                 .extrude(platformBaseExtrude)
        bb = platform.BoundBox
        self.AddPiece(bb.XLength,bb.YLength,"%.3fin Wood Block"%(platformBaseHeight/25.4))
        platformTopExtrude = Base.Vector(0,0,Units.mm(Units.HOScale(12)))
        p1origin = origin.add(Base.Vector(
                                0,
                                self.__CombinedTrackAndPlatformWidth-\
                                    self.__PlatformWidth,
                                self.__PlatformHeight-\
                                    Units.mm(Units.HOScale(12))))
        platform = platform.fuse(
            Part.makePlane(self.__LongPlatformLength,
                           self.__PlatformWidth,
                           p1origin)\
                 .extrude(platformTopExtrude))
        l1riselen = self.__TotalStairLength(self.__StairLandingRiseMax,0)
        stairwellcutLen = (platformStairLen-l1riselen)
        stairwellcut = Part.makePlane(stairwellcutLen,
                                      self.__PlatformStairWidth,
                                      self.platform1StairOrigin.add(Base.Vector(
                                            l1riselen,
                                            0,
                                            self.__StairLandingRiseMax)))\
                          .extrude(Base.Vector(0,0,self.__StairLandingRiseMax*2))
        self.platform1 = platform.cut(stairwellcut)
        stairShelterOrigin = Base.Vector(self.platform1StairOrigin.x+\
                                                    l1riselen,
                                                    self.platform1StairOrigin.y+\
                                                        self.__PlatformStairWidth,
                                                    origin.z+self.__PlatformHeight)
        stairShelter = Part.makePlane(self.__PlatformRoofHeight-self.__PlatformHeight,
                                      self.__PlatformStairWidth,
                                      stairShelterOrigin,
                                      Base.Vector(1,0,0))\
               .extrude(Base.Vector(-self.__GlassWallWidth,0,0))
        bb = stairShelter.BoundBox
        self.AddPiece(bb.YLength,bb.ZLength,".040 Clear Copolyester (SSC-104)")
        LaserCut.CopolysterSSC_104Cut.AddCut(stairShelter)
        ss1A = Part.makePlane(
                self.__PlatformRoofHeight-self.__PlatformHeight,
                stairwellcutLen+self.__PlatformStairWidth+(2*self.__GlassWallWidth),
                stairShelterOrigin.add(Base.Vector(-self.__GlassWallWidth,
                                                   -self.__PlatformStairWidth,0)),
                Base.Vector(0,1,0)).extrude(Base.Vector(0,-self.__GlassWallWidth,0))
        stairShelter = stairShelter.fuse(ss1A)
        bb = ss1A.BoundBox
        self.AddPiece(bb.XLength,bb.ZLength,".040 Clear Copolyester (SSC-104)")
        LaserCut.CopolysterSSC_104Cut.AddCut(ss1A)
        ss1A = Part.makePlane(self.__PlatformRoofHeight-self.__PlatformHeight,
                                      self.__PlatformStairWidth,
                                      stairShelterOrigin.add(Base.Vector(stairwellcutLen+self.__PlatformStairWidth,0,0)),
                                      Base.Vector(1,0,0))\
               .extrude(Base.Vector(self.__GlassWallWidth,0,0))
        bb = ss1A.BoundBox
        stairShelterDoorOrigin = Base.Vector(bb.XMin,
                                             bb.YMin+
                                                ((self.__PlatformStairWidth-
                                                    self.__SingleDoorCutWidth)/2),
                                             bb.ZMin)
        ss1A = ss1A.cut(
            self.__singleDoorCut(stairShelterDoorOrigin,
                                 self.__GlassWallWidth))
        LaserCut.CopolysterSSC_104Cut.AddCut(ss1A)
        self.stair1Shelter = stairShelter.fuse(ss1A)
        self.AddPart("Tichy Train Group #8195 Single Glass Door")
        self.AddPiece(bb.YLength,bb.ZLength,".040 Clear Copolyester (SSC-104)")
        postSkip2 = (stairShelterOrigin.x-self.__GlassWallWidth,
                      stairShelterOrigin.x+stairwellcutLen+self.__PlatformStairWidth+self.__GlassWallWidth)
        stairShelterOrigin = Base.Vector(self.platform2StairOrigin.x+\
                                                    l1riselen,
                                                    self.platform2StairOrigin.y+\
                                                        self.__PlatformStairWidth,
                                                    origin.z+self.__PlatformHeight)
        stairShelter = Part.makePlane(self.__PlatformRoofHeight-self.__PlatformHeight,
                                      self.__PlatformStairWidth,
                                      stairShelterOrigin,
                                      Base.Vector(1,0,0))\
               .extrude(Base.Vector(-self.__GlassWallWidth,0,0))
        bb = stairShelter.BoundBox
        self.AddPiece(bb.YLength,bb.ZLength,".040 Clear Copolyester (SSC-104)")
        LaserCut.CopolysterSSC_104Cut.AddCut(stairShelter)
        ss1A = Part.makePlane(
                self.__PlatformRoofHeight-self.__PlatformHeight,
                stairwellcutLen+self.__PlatformStairWidth+(2*self.__GlassWallWidth),
                stairShelterOrigin.add(Base.Vector(-self.__GlassWallWidth,
                                                   self.__GlassWallWidth,0)),
                Base.Vector(0,1,0)).extrude(Base.Vector(0,-self.__GlassWallWidth,0))
        stairShelter = stairShelter.fuse(ss1A)
        bb = ss1A.BoundBox
        self.AddPiece(bb.XLength,bb.ZLength,".040 Clear Copolyester (SSC-104)")
        LaserCut.CopolysterSSC_104Cut.AddCut(ss1A)
        ss1A = Part.makePlane(self.__PlatformRoofHeight-self.__PlatformHeight,
                                      self.__PlatformStairWidth,
                                      stairShelterOrigin.add(Base.Vector(stairwellcutLen+self.__PlatformStairWidth,0,0)),
                                      Base.Vector(1,0,0))\
               .extrude(Base.Vector(self.__GlassWallWidth,0,0))
        bb = ss1A.BoundBox
        stairShelterDoorOrigin = Base.Vector(bb.XMin,
                                             bb.YMin+
                                                ((self.__PlatformStairWidth-
                                                    self.__SingleDoorCutWidth)/2),
                                             bb.ZMin)
        ss1A = ss1A.cut(
            self.__singleDoorCut(stairShelterDoorOrigin,
                                 self.__GlassWallWidth))
        LaserCut.CopolysterSSC_104Cut.AddCut(ss1A)
        self.stair2Shelter = stairShelter.fuse(ss1A)
        self.AddPiece(bb.YLength,bb.ZLength,".040 Clear Copolyester (SSC-104)")
        self.AddPart("Tichy Train Group #8195 Single Glass Door")
        platform = Part.makePlane(self.__LongPlatformLength,
                                  platformBaseWidth,
                                  origin)\
                 .extrude(platformBaseExtrude)
        bb = platform.BoundBox
        self.AddPiece(bb.XLength,bb.YLength,"%.3fin Wood Block"%(platformBaseHeight/25.4))
        platform = platform.fuse(
            Part.makePlane(self.__LongPlatformLength,
                           self.__PlatformWidth,
                           origin.add(
                            Base.Vector(
                                0,
                                0,
                                self.__PlatformHeight-\
                                    Units.mm(Units.HOScale(12)))))\
                 .extrude(platformTopExtrude))
        stairwellcut = Part.makePlane(stairwellcutLen,
                                      self.__PlatformStairWidth,
                                      self.platform2StairOrigin.add(Base.Vector(
                                            l1riselen,
                                            0,
                                            self.__StairLandingRiseMax)))\
                          .extrude(Base.Vector(0,0,self.__StairLandingRiseMax*2))
        self.platform2 = platform.cut(stairwellcut)
        #debug("*** UnderStation.__init__(): platform stairwell bottom is %d",self.platform2StairOrigin.z+self.__StairLandingRiseMax)
        p1RoofOrigin = Base.Vector(p1origin.x,p1origin.y,
                                   origin.z+self.__PlatformRoofHeight)
        p1roof = Part.makePlane(self.__LongPlatformLength,
                                self.__PlatformWidth,
                                p1RoofOrigin).extrude(Base.Vector(0,0,self.__PlatformRoofThickness))
        self.platform1 = self.platform1.fuse(p1roof).cut(self.platform1Elevator.shaft)
        p2RoofOrigin = Base.Vector(origin.x,origin.y,
                                   origin.z+self.__PlatformRoofHeight)
        p2roof = Part.makePlane(self.__LongPlatformLength,
                                self.__PlatformWidth,
                                p2RoofOrigin).extrude(Base.Vector(0,0,self.__PlatformRoofThickness))
        self.platform2 = self.platform2.fuse(p2roof).cut(self.platform2Elevator.shaft)
        postEnd = p1origin.x+self.__LongPlatformLength
        postX = p1origin.x+self.__PostOffset-self.__PostSpacing
        postLength = p1RoofOrigin.z-p1origin.z-Units.mm(Units.HOScale(12))
        while postX < postEnd-self.__PostSpacing:
            postX = postX + self.__PostSpacing
            #debug("*** postX = %f, postEnd is %f",postX,postEnd)
            if postX+self.__PostDiameter/2 > postSkip1[0] and \
               postX-self.__PostDiameter/2 < postSkip1[1]:
                continue
            #if postX+self.__PostDiameter/2 > postSkip2[0] and \
            #   postX-self.__PostDiameter/2 < postSkip2[1]:
            #    continue
            post1Orig = Base.Vector(postX,p1origin.y+self.__PlatformWidth/2,origin.z+self.__PlatformHeight)
            post1 = Part.makeCylinder(self.__PostDiameter/2,postLength,post1Orig)
            self.platform1 = self.platform1.fuse(post1)
            post2Orig = Base.Vector(postX,origin.y+self.__PlatformWidth/2,origin.z+self.__PlatformHeight)
            post2 = Part.makeCylinder(self.__PostDiameter/2,postLength,post2Orig)
            self.platform2 = self.platform2.fuse(post2)
        self.AddPart("Walthers Cornerstone Part # 933-3175")
        wall = Part.makePlane(self.__PlatformRoofHeight+\
                                self.__TotalStationHeight+\
                                self.__StationUnderOffset+\
                                self.__PlatformRoofThickness,
                              self.__LongPlatformLength+
                                (2*self.__MainWallWidth),
                              origin.add(
                                Base.Vector(-self.__MainWallWidth,
                                            self.__CombinedTrackAndPlatformWidth,
                                            -(self.__TotalStationHeight+self.__StationUnderOffset))),
                              Base.Vector(0,1,0))\
            .extrude(Base.Vector(0,self.__MainWallWidth,0))
        bb = wall.BoundBox
        self.AddPiece(bb.XLength,bb.ZLength,".080 Styreen (SSS-10824)") 
        wall = wall.cut(Part.makePlane(self.__TotalStationHeight,
                                       self.__ShortPlatformLength-
                                        (3*Elevator.ShaftLength)+
                                        self.__MainWallWidth,
                                       origin.add(
                                Base.Vector(-self.__MainWallWidth,
                                            self.__CombinedTrackAndPlatformWidth,
                                            -(self.__TotalStationHeight+self.__StationUnderOffset))),
                              Base.Vector(0,1,0))\
            .extrude(Base.Vector(0,self.__MainWallWidth,0)))
        wall = wall.cut(Part.makePlane(Units.mm(.25),
                                       self.__LongPlatformLength+
                                        (2*self.__MainWallWidth),
                                       origin.add(
                                        Base.Vector(-self.__MainWallWidth,
                                                    self.__CombinedTrackAndPlatformWidth,
                                                    -Units.mm(.25))),
                                       Base.Vector(0,1,0))\
            .extrude(Base.Vector(0,self.__MainWallWidth,0)))
        LaserCut.StyreneSSS_10824Cut.AddCut(wall)
        wall1 = Part.makePlane(self.__TotalStationHeight,
                                        self.__CombinedTrackAndPlatformWidth+\
                                            (2*self.__MainWallWidth)+
                                            Elevator.ShaftLength+
                                            self.__StreetStairWidth+.11,
                                        origin.add(
                                            Base.Vector(0,self.__CombinedTrackAndPlatformWidth+
                                                            (2*self.__MainWallWidth)+
                                                            Elevator.ShaftLength+
                                                            self.__StreetStairWidth,
                                                   -(self.__TotalStationHeight+self.__StationUnderOffset))),
                                        Base.Vector(1,0,0))\
                            .extrude(Base.Vector(-self.__MainWallWidth,0,0))
        LaserCut.StyreneSSS_10824Cut.AddCut(wall1)
        wall = wall.fuse(wall1)
        bb = wall1.BoundBox
        self.AddPiece(bb.YLength,bb.ZLength,".080 Styreen (SSS-10824)")
        wall1 = Part.makePlane(self.__TotalStationHeight,
                                        self.__CombinedTrackAndPlatformWidth-(2*self.__PlatformStairWidth),
                                        self.platform1StairOrigin,
                                        Base.Vector(1,0,0))\
                              .extrude(Base.Vector(self.__MainWallWidth,0,0))
        LaserCut.StyreneSSS_10824Cut.AddCut(wall1)
        wall = wall.fuse(wall1)
        bb = wall1.BoundBox
        self.AddPiece(bb.YLength,bb.ZLength,".080 Styreen (SSS-10824)")
        wall1 = Part.makePlane(self.__TotalStationHeight,
                                        self.platform1StairOrigin.x-\
                                            elevator2Origin.x,
                                        elevator2Origin.add(
                                            Base.Vector(0,
                                                        Elevator.ShaftLength,
                                                        0)),
                                        Base.Vector(0,1,0))\
                        .extrude(Base.Vector(0,self.__MainWallWidth,0))
        bb = wall1.BoundBox
        wlen = bb.XLength-Elevator.ShaftWidth
        doff = Elevator.ShaftWidth+((wlen-self.__DoubleDoorCutWidth)/2)
        doorOrigin = Base.Vector(bb.XMin+doff,
                                 bb.YMin,
                                 bb.ZMin)
        wall1 = wall1.cut(
                self.__doubleDoorCutY(doorOrigin,self.__MainWallWidth))
        LaserCut.StyreneSSS_10824Cut.AddCut(wall1)
        wall = wall.fuse(wall1)
        self.AddPart("Tichy Train Group #8198 Double Glass Door")
        self.AddPiece(bb.XLength,bb.ZLength,".080 Styreen (SSS-10824)")
        wall1 = Part.makePlane(self.__TotalStationHeight,
                                        self.platform1StairOrigin.x-\
                                            elevator2Origin.x,
                                        elevator1Origin.add(
                                            Base.Vector(0,
                                                        0,
                                                        0)),
                                        Base.Vector(0,1,0))\
                        .extrude(Base.Vector(0,-self.__MainWallWidth,0))
        bb = wall1.BoundBox
        wlen = bb.XLength-Elevator.ShaftWidth
        doff = Elevator.ShaftWidth+((wlen-self.__DoubleDoorCutWidth)/2)
        doorOrigin = Base.Vector(bb.XMin+doff,
                                 bb.YMin,
                                 bb.ZMin)
        wall1 = wall1.cut(
                self.__doubleDoorCutY(doorOrigin,self.__MainWallWidth))
        LaserCut.StyreneSSS_10824Cut.AddCut(wall1)
        wall = wall.fuse(wall1)
        self.AddPart("Tichy Train Group #8198 Double Glass Door")
        self.AddPiece(bb.XLength,bb.ZLength,".080 Styreen (SSS-10824)")
        ceiling = Part.makePlane((self.platform1StairOrigin.x-origin.x)+\
                                    (2*self.__MainWallWidth),
                                 self.__CombinedTrackAndPlatformWidth,
                                 origin.add(
                                    Base.Vector(
                                        -self.__MainWallWidth,
                                        0,
                                        -self.__StationUnderOffset)))\
                     .extrude(Base.Vector(0,0,self.__MainWallWidth))
        bb = ceiling.BoundBox
        self.AddPiece(bb.XLength,bb.YLength,".080 Styreen (SSS-10824)")
        ceiling = ceiling.cut(self.platform1Elevator.shaft)
        ceiling = ceiling.cut(self.platform2Elevator.shaft)
        LaserCut.StyreneSSS_10824Cut.AddCut(ceiling)
        stairwaywall1 = Part.makePlane(self.__TotalStationHeight+\
                                        self.__StationUnderOffset-
                                        Units.mm(.25),
                                       platformStairLen-self.__MainWallWidth,
                                       self.platform1StairOrigin.add(
                                        Base.Vector(self.__MainWallWidth,0,0)),
                                       Base.Vector(0,1,0))\
                .extrude(Base.Vector(0,-self.__MainWallWidth,0))
        bb = stairwaywall1.BoundBox
        self.AddPiece(bb.XLength,bb.ZLength,".080 Styreen (SSS-10824)")
        LaserCut.StyreneSSS_10824Cut.AddCut(stairwaywall1)
        stairwaywall2 = Part.makePlane(self.__TotalStationHeight+\
                                        self.__StationUnderOffset-
                                        Units.mm(.25),
                                       platformStairLen-self.__MainWallWidth,
                                       self.platform2StairOrigin.add(
                                        Base.Vector(self.__MainWallWidth,
                                                    self.__PlatformStairWidth,0)),
                                       Base.Vector(0,1,0))\
                .extrude(Base.Vector(0,self.__MainWallWidth,0))
        bb = stairwaywall1.BoundBox
        self.AddPiece(bb.XLength,bb.ZLength,".080 Styreen (SSS-10824)")
        LaserCut.StyreneSSS_10824Cut.AddCut(stairwaywall2)
        stairbackwall = Part.makePlane(self.__StationUnderOffset-
                                        Units.mm(.25)-
                                        self.__MainWallWidth,
                                       self.__CombinedTrackAndPlatformWidth,
                                       self.platform1StairOrigin.add(
                                        Base.Vector(0,self.__PlatformStairWidth,self.__TotalStationHeight+self.__MainWallWidth)),
                                       Base.Vector(1,0,0))\
                       .extrude(Base.Vector(self.__MainWallWidth,0,0))
        bb = stairbackwall.BoundBox
        self.AddPiece(bb.YLength,bb.ZLength,".080 Styreen (SSS-10824)")
        LaserCut.StyreneSSS_10824Cut.AddCut(stairbackwall)
        self.walls = wall.fuse(ceiling).fuse(stairwaywall1
                ).fuse(stairwaywall2).fuse(stairbackwall)
        rearHeight = self.streetElevator.shaft.BoundBox.ZLength
        rearwall1 = Part.makePlane(rearHeight,
                                   self.__LongPlatformLength+
                                    (2*self.__MainWallWidth),
                                   origin.add(Base.Vector(
                                        -self.__MainWallWidth,
                                        self.__TotalStationDepth+
                                          self.__MainWallWidth,
                                        -(self.__TotalStationHeight+
                                          self.__StationUnderOffset))),
                                   Base.Vector(0,1,0)
                        ).extrude(Base.Vector(0,self.__MainWallWidth,0))
        bb = rearwall1.BoundBox
        self.AddPiece(bb.XLength,bb.ZLength,".080 Styreen (SSS-10824)") 
        rearwall1 = rearwall1.cut(Part.makePlane(Units.mm(.25),
                                                 self.__LongPlatformLength+
                                                    (2*self.__MainWallWidth),
                                                 origin.add(Base.Vector(
                                                    -self.__MainWallWidth,
                                                    self.__TotalStationDepth+
                                                        self.__MainWallWidth,
                                                    -Units.mm(.25))),
                                                  Base.Vector(0,1,0)
                          ).extrude(Base.Vector(0,self.__MainWallWidth,0)))
        LaserCut.StyreneSSS_10824Cut.AddCut(rearwall1)
        self.walls = self.walls.fuse(rearwall1)
        rearwall1 = Part.makePlane(rearHeight,
                                   self.__LongPlatformLength-
                                    (3*self.__StreetStairWidth)+
                                    Elevator.ShaftWidth,
                                   origin.add(Base.Vector(
                                        self.__StreetStairWidth,
                                        self.__TotalStationDepth-
                                          self.__StreetStairWidth,
                                        -(self.__TotalStationHeight+
                                          self.__StationUnderOffset))),
                                   Base.Vector(0,1,0)
                        ).extrude(Base.Vector(0,self.__MainWallWidth,0))
        rearwall1 = rearwall1.cut(Part.makePlane(Units.mm(.25),
                                                 self.__LongPlatformLength-
                                                    (3*self.__StreetStairWidth)+
                                                    Elevator.ShaftWidth,
                                                 origin.add(Base.Vector(
                                                    self.__StreetStairWidth,
                                                    self.__TotalStationDepth-
                                                        self.__StreetStairWidth,
                                                    -Units.mm(.25))),
                                                 Base.Vector(0,1,0)
                         ).extrude(Base.Vector(0,self.__MainWallWidth,0)))
        bb = rearwall1.BoundBox
        self.AddPiece(bb.XLength,bb.ZLength,".080 Styreen (SSS-10824)") 
        LaserCut.StyreneSSS_10824Cut.AddCut(rearwall1)
        self.walls = self.walls.fuse(rearwall1)
        entryFloor1 = Part.makePlane(58.79,Elevator.ShaftLength+
                                            self.__MainWallWidth,
                                     origin.add(Base.Vector(
                                        500.01,
                                        207.49,
                                        self.__CurbHeight-
                                         self.__MainWallWidth))
                  ).extrude(Base.Vector(0,0,self.__MainWallWidth))
        bb = entryFloor1.BoundBox
        self.AddPiece(bb.XLength,bb.YLength,".080 Styreen (SSS-10824)")
        LaserCut.StyreneSSS_10824Cut.AddCut(entryFloor1)
        self.walls = self.walls.fuse(entryFloor1)
        entryFloor1 = Part.makePlane(12.59,self.__StreetStairWidth,
                                     origin.add(Base.Vector(
                                        546.21,241.54,
                                        self.__CurbHeight-
                                            self.__MainWallWidth))
                  ).extrude(Base.Vector(0,0,self.__MainWallWidth)) 
        bb = entryFloor1.BoundBox
        self.AddPiece(bb.XLength,bb.YLength,".080 Styreen (SSS-10824)")
        LaserCut.StyreneSSS_10824Cut.AddCut(entryFloor1)
        self.walls = self.walls.fuse(entryFloor1) 
        entryWall1 = Part.makePlane(51.38,
                                    Elevator.ShaftLength+
                                        (1*self.__MainWallWidth)+
                                        self.__StreetStairWidth,
                                    origin.add(Base.Vector(558.8,283.58,0)),
                                    Base.Vector(1,0,0)
                   ).extrude(Base.Vector(self.__MainWallWidth,0,0))
        bb = entryWall1.BoundBox
        doorOrigin = Base.Vector(bb.XMin,
                                 bb.YMin+
                                    ((bb.YLength-self.__DoubleDoorCutWidth)/2),
                                 bb.ZMin)
        entryWall1 = entryWall1.cut(
                self.__doubleDoorCutX(doorOrigin,self.__MainWallWidth))
        LaserCut.StyreneSSS_10824Cut.AddCut(entryWall1)
        self.AddPiece(bb.YLength,bb.ZLength,".080 Styreen (SSS-10824)")
        self.walls = self.walls.fuse(entryWall1)
        self.AddPart("Tichy Train Group #8198 Double Glass Door")
        roof = Part.makePlane(self.__LongPlatformLength+
                                    (2*self.__MainWallWidth),
                              Elevator.ShaftLength+
                                        (2*self.__MainWallWidth)+
                                        self.__StreetStairWidth,
                              origin.add(Base.Vector(-self.__MainWallWidth,
                                                     207.49,
                                                     51.38))
                    ).extrude(Base.Vector(0,0,self.__MainWallWidth))
        bb = roof.BoundBox
        self.AddPiece(bb.XLength,bb.YLength,".080 Styreen (SSS-10824)")
        LaserCut.StyreneSSS_10824Cut.AddCut(roof)
        self.walls = self.walls.fuse(roof)
        backwall = Part.makePlane(self.__StationUnderOffset+51.38,
                                  Elevator.ShaftLength+
                                    (1*self.__MainWallWidth)+
                                    self.__StreetStairWidth,
                                  origin.add(Base.Vector(-self.__MainWallWidth,
                                                         self.__CombinedTrackAndPlatformWidth+\
                                            (2*self.__MainWallWidth)+
                                            Elevator.ShaftLength+
                                            self.__StreetStairWidth+.11,
                                            -self.__StationUnderOffset)),
                                  Base.Vector(1,0,0)
                     ).extrude(Base.Vector(self.__MainWallWidth,0,0))
        bb = backwall.BoundBox
        self.AddPiece(bb.ZLength,bb.YLength,".080 Styreen (SSS-10824)")
        backwall = backwall.cut(Part.makePlane(Units.mm(.25),
                                               Elevator.ShaftLength+
                                                (1*self.__MainWallWidth)+
                                                self.__StreetStairWidth,
                                               origin.add(Base.Vector(-self.__MainWallWidth,
                                                         self.__CombinedTrackAndPlatformWidth+
                                                            (2*self.__MainWallWidth)+
                                                         Elevator.ShaftLength+
                                                           self.__StreetStairWidth+.11,
                                                         -Units.mm(.25))),
                                                Base.Vector(1,0,0)
                     ).extrude(Base.Vector(self.__MainWallWidth,0,0)))
        LaserCut.StyreneSSS_10824Cut.AddCut(backwall)
        self.walls = self.walls.fuse(backwall)
        #self.AddPart("Tichy Train Group #8195 Single Glass Door",4)
        #self.AddPart("Tichy Train Group #8198 Double Glass Door",3)
        self.AddPart("Tichy Train Group #8193 Strap Railing") 
        
    def show(self,doc=None):
        if doc==None:
            doc = App.activeDocument()
        self.streetElevator.show(doc)
        obj = doc.addObject("Part::Feature",self.name+"_StreetStairs")
        obj.Shape = self.streetStair
        obj.Label=self.name+"_StreetStairs"
        obj.ViewObject.ShapeColor=self.__StairsColor
        obj = doc.addObject("Part::Feature",self.name+"_Platform1Stairs")
        obj.Shape = self.platform1Stair
        obj.Label=self.name+"_Platform1Stairs"
        obj.ViewObject.ShapeColor=self.__StairsColor
        obj = doc.addObject("Part::Feature",self.name+"_Platform2Stairs")
        obj.Shape = self.platform2Stair
        obj.Label=self.name+"_Platform2Stairs"
        obj.ViewObject.ShapeColor=self.__StairsColor
        obj = doc.addObject("Part::Feature",self.name+"_Floor")
        obj.Shape = self.stationFloor
        obj.Label=self.name+"_Floor"
        obj.ViewObject.ShapeColor=self.__FloorColor
        self.platform1Elevator.show(doc)
        self.platform2Elevator.show(doc)
        obj = doc.addObject("Part::Feature",self.name+"_Platform1")
        obj.Shape = self.platform1
        obj.Label=self.name+"_Platform1"
        obj.ViewObject.ShapeColor=self.__StairsColor
        obj = doc.addObject("Part::Feature",self.name+"_Platform2")
        obj.Shape = self.platform2
        obj.Label=self.name+"_Platform2"
        obj.ViewObject.ShapeColor=self.__StairsColor
        obj = doc.addObject("Part::Feature",self.name+"_Platform1StairShelter")
        obj.Shape = self.stair1Shelter
        obj.Label=self.name+"_Platform1StairShelter"
        obj.ViewObject.ShapeColor=(1.0,1.0,1.0)
        obj.ViewObject.Transparency=90
        obj = doc.addObject("Part::Feature",self.name+"_Platform2StairShelter")
        obj.Shape = self.stair2Shelter
        obj.Label=self.name+"_Platform2StairShelter"
        obj.ViewObject.ShapeColor=(1.0,1.0,1.0)
        obj.ViewObject.Transparency=90
        obj = doc.addObject("Part::Feature",self.name+"_Platform1ElevatorShelter")
        obj.Shape = self.elevator1Shelter
        obj.Label=self.name+"_Platform1ElevatorShelter"
        obj.ViewObject.ShapeColor=(1.0,1.0,1.0)
        obj.ViewObject.Transparency=90
        obj = doc.addObject("Part::Feature",self.name+"_Platform2ElevatorShelter")
        obj.Shape = self.elevator2Shelter
        obj.Label=self.name+"_Platform2ElevatorShelter"
        obj.ViewObject.ShapeColor=(1.0,1.0,1.0)
        obj.ViewObject.Transparency=90
        obj = doc.addObject("Part::Feature",self.name+"_Walls")
        obj.Shape = self.walls
        obj.Label=self.name+"_Walls"
        obj.ViewObject.ShapeColor=(.75,.75,.75)
        #obj = doc.addObject("Part::Feature",self.name+"_Door")
        #obj.Shape = self.door
        #obj.ViewObject.ShapeColor=(1.0,0.0,0.0)

if __name__ == '__main__':
    if "UnderStation" in App.listDocuments().keys():
        App.closeDocument("UnderStation")
    doc = App.newDocument("UnderStation")
    doc = App.activeDocument()
    station = UnderStation("Station",Base.Vector(0,0,0))
    station.show(doc)
    #Gui.activeDocument().activeView().viewTop()
    #Gui.SendMsgToActiveView("ViewFit")
    UnderStation.ListParts("UnderStationParts.csv")
    UnderStation.ListCuts("UnderStationCuts.csv")    
    LaserCut.CopolysterSSC_104Cut.Flush()
    LaserCut.BricksPS_97Cut.Flush()
    LaserCut.StyreneSSS_10824Cut.Flush()
