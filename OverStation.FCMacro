#*****************************************************************************
#
#  System        : 
#  Module        : 
#  Object Name   : $RCSfile$
#  Revision      : $Revision$
#  Date          : $Date$
#  Author        : $Author$
#  Created By    : Robert Heller
#  Created       : 2026-04-23 14:00:08
#  Last Modified : <260510.1259>
#
#  Description	
#
#  Notes
#
#  History
#	
#*****************************************************************************
#
#    Copyright (C) 2026  Robert Heller D/B/A Deepwoods Software
#			51 Locke Hill Road
#			Wendell, MA 01379-9728
#
#    This program is free software; you can redistribute it and/or modify
#    it under the terms of the GNU General Public License as published by
#    the Free Software Foundation; either version 2 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program; if not, write to the Free Software
#    Foundation, Inc., 675 Mass Ave, Cambridge, MA 02139, USA.
#
# 
#
#*****************************************************************************


import FreeCAD as App
import Part, TechDraw, Mesh
from FreeCAD import Base

import os
import sys
sys.path.append(os.path.dirname(__file__))
import csv
import math
import Units
from debug import debug

import LaserCut

def NormalizeMM(x):
    return round(x,3)

class BOMHelper(object):
    __BOM = dict()
    @classmethod
    def AddPiece(cls,width,height,kind):
        key = (NormalizeMM(width),NormalizeMM(height),kind)
        if key in cls.__BOM:
            cls.__BOM[key] += 1
        else:
            cls.__BOM[key] = 1
    @classmethod
    def _normPartSizeMM(cls,t):
        return ("%.3fx%.3f" % t)
    @staticmethod
    def _inch(mm):
        return mm / 25.4
    @classmethod
    def _normPartSizeIN(cls,t):
        X, Y = t
        return ("%.4fx%.4f" % (cls._inch(X), cls._inch(Y)))
    _units = 'in'
    @classmethod
    def SetUnits(cls,units):
        if units == 'in' or units == 'mm':
            cls._units = units
        else:
            raise RuntimeError("Unsupport units!")
    @classmethod
    def GetUnits(cls):
        return cls._units
    @classmethod
    def _normPartSize(cls,t):
        if cls._units == 'in':
            return cls._normPartSizeIN(t)
        elif cls._units == 'mm':
            return BOMHelper._normPartSizeMM(t)
        else:
            raise RuntimeError("Unsupport units!")
    @classmethod
    def ListCuts(cls,filename):
        keys = list(cls.__BOM.keys())
        keys.sort()
        f = open(filename,"w")
        w = csv.writer(f)
        w.writerow([("Size (%s)" % cls._units),"Kind","Count"])
        for key in keys:
            X, Y, kind = key
            w.writerow([cls._normPartSize((X,Y)),kind,cls.__BOM[key]])
        f.close()

class PartsHelper(object):
    __BOP = dict()
    @classmethod
    def AddPart(cls,part,count=1):
        if part in cls.__BOP:
            cls.__BOP[part] += count
        else:
            cls.__BOP[part] = count
    @classmethod
    def ListParts(cls,filename):
        parts = list(cls.__BOP.keys())
        parts.sort()
        f = open(filename,"w")
        w = csv.writer(f)
        w.writerow(["Part","Count"])
        for part in parts:
            w.writerow([ part, cls.__BOP[part] ])
        f.close()

class Elevator(object):
    __CabinWidth  = Units.HOScale(1600)
    __CabinLength = Units.HOScale(2100)
    ShaftWidth  = Units.HOScale(2200)
    ShaftLength = Units.HOScale(2800)
    __DoorWidth   = Units.HOScale(1000)
    __HeadRoom    = Units.HOScale(Units.mm(100))
    __Mechanical  = Units.HOScale(Units.mm(50))
    __ShaftColor  = tuple([0xaa/255.0,0xaa/255.0,0xaa/255.0])
    def __init__(self,name,origin,liftheight):
        self.name = name
        if not isinstance(origin,Base.Vector):
            raise RuntimeError("origin is not a Vector!")
        self.origin = origin
        self.shaft = Part.makePlane(self.ShaftWidth,
                                    self.ShaftLength,
                                    self.origin)\
           .extrude(Base.Vector(0,0,liftheight+\
                                    (self.__HeadRoom*1.2)+\
                                    self.__Mechanical))
    def show(self,doc=None):
        if doc==None:
            doc = App.activeDocument()
        obj = doc.addObject("Part::Feature",self.name+"_shaft")
        obj.Shape = self.shaft
        obj.Label=self.name+"_shaft"
        obj.ViewObject.ShapeColor=self.__ShaftColor

class OverStation(BOMHelper, PartsHelper): 
    # Walthers Cornerstone Part # 933-3175
    # Butterfly Style Station Platform Shelter 11 x 2-1/8 x 2-1/4"
    __ShortPlatformLength = Units.mm(11)
    # 2X end to end
    __LongPlatformLength  = Units.mm(22)
    __PlatformWidth       = Units.mm(2.125)
    __PlatformRoofHeight  = Units.mm(2.25)
    # Raised platform (level boarding)
    __PlatformHeight      = Units.mm(Units.HOScale(51))
    # Walthers Cornerstone Part # 933-3175
    # Butterfly Style Station Platform Shelter 11 x 2-1/8 x 2-1/4"
    __ShortPlatformLength = Units.mm(11)
    # 2X end to end
    __LongPlatformLength  = Units.mm(22)
    __PlatformWidth       = Units.mm(2.125)
    __PlatformRoofHeight  = Units.mm(2.25)
    # Raised platform (level boarding)
    __PlatformHeight      = Units.mm(Units.HOScale(51))
    # Walthers Cornerstone Part # 933-3175
    # Butterfly Style Station Platform Shelter 11 x 2-1/8 x 2-1/4"
    __ShortPlatformLength = Units.mm(11)
    # 2X end to end
    __LongPlatformLength  = Units.mm(22)
    __PlatformWidth       = Units.mm(2.125)
    __PlatformRoofHeight  = Units.mm(2.25)
    # Raised platform (level boarding)
    __PlatformHeight      = Units.mm(Units.HOScale(51))
    # Walthers Cornerstone Part # 933-3175
    # Butterfly Style Station Platform Shelter 11 x 2-1/8 x 2-1/4"
    __ShortPlatformLength = Units.mm(11)
    # 2X end to end
    __LongPlatformLength  = Units.mm(22)
    __PlatformWidth       = Units.mm(2.125)
    __PlatformRoofHeight  = Units.mm(2.25)
    # Raised platform (level boarding)
    __PlatformHeight      = Units.mm(Units.HOScale(51))
    # Walthers Cornerstone Part # 933-3175
    # Butterfly Style Station Platform Shelter 11 x 2-1/8 x 2-1/4"
    __ShortPlatformLength = Units.mm(11)
    # 2X end to end
    __LongPlatformLength  = Units.mm(22)
    __PlatformWidth       = Units.mm(2.125)
    __PlatformRoofHeight  = Units.mm(2.25)
    # Raised platform (level boarding)
    __PlatformHeight      = Units.mm(Units.HOScale(51))
    __CombinedTrackAndPlatformWidth = Units.mm(8.1)
    __TotalStationLength = Units.mm(22.5)
    __MainWallWidth = .080*25.4
    __GlassWallWidth  = .040*25.4 
    __PlastructPS_97Thick = .020*25.4
    __PlatformRoofThickness = .080*25.4
    __CeilingAndRoofThickness = .020*25.4
    __StairRiser         = Units.mm(Units.HOScale(5.5))
    __StairTread         = Units.mm(Units.HOScale(11))
    __PostOffset         = Units.mm(Units.HOScale(Units.inches(5)))
    __PostSpacing        = Units.mm(Units.HOScale(Units.inches(10)))
    __PostDiameter       = Units.mm(Units.HOScale(Units.inches(2)))
    __BridgeWidth        = Units.mm(Units.HOScale(Units.inches(24)))
    __MainStationWidth   = Units.mm(Units.HOScale(Units.inches(67)))
    __RestroomWidth      = Units.mm(Units.HOScale(Units.inches(20)))
    __OfficeWidth        = Units.mm(Units.HOScale(Units.inches(7)))
    __TicketWindowSpaceWidth = Units.mm(Units.HOScale(Units.inches(10)))
    __TicketWindowWidth  = Units.mm(Units.HOScale(Units.inches(8)))
    __TicketCounterHeight = Units.mm(Units.HOScale(Units.inches(4)))
    __TicketWindowHeight = Units.mm(Units.HOScale(Units.inches(3)))
    # from UG-2832HSWEG02.pdf (SAS1-B026-B, Univision Technology Inc.)
    __DepartureBoardWidth = 30
    __DepartureBoardHeight = 11.5
    __DepartureBoardZOffset = Units.mm(Units.HOScale(Units.inches(5)))
    __DepartureBoardXOffset = Units.mm(Units.HOScale(Units.inches(20+2)))
    __TicketCounterXOffset  = Units.mm(Units.HOScale(Units.inches(20+15)))
    @property
    def __InnerBlockWallLength(self):
        return (2*self.__RestroomWidth)+self.__OfficeWidth+\
                    self.__TicketWindowSpaceWidth
    @property
    def __InnerBlockWallXOff(self):
        return (self.__MainStationWidth-self.__InnerBlockWallLength)/2
    __MainStationLength  = Units.mm(Units.HOScale(Units.inches(40)))
    __InnerBlockWallYOff      = Units.mm(Units.HOScale(Units.inches(30)))
    @property
    def __RestroomBackWallLength(self):
        return self.__MainStationLength-self.__InnerBlockWallYOff-\
                 (2*self.__MainWallWidth)
    __RestroomBackXOff   = Units.mm(Units.HOScale(Units.inches(20)))
    __RestroomPrivacyWallLength = Units.mm(Units.HOScale(Units.inches(6)))
    __RestroomPrivacyWallDX = Units.mm(Units.HOScale(Units.inches(6)))
    __MainStationXOffset = -Units.mm(Units.HOScale(Units.inches(10)))
    __StationHeight      = Units.mm(Units.HOScale(Units.inches(12)))
    @property
    def __StairRiseRatio(self):
        return self.__StairTread/self.__StairRiser
    __StairLandingRiseMax = Units.mm(Units.inches(Units.HOScale( 12 )))
    __StairHeadRoomMin    = Units.mm(Units.HOScale(80))
    __PlatformStairWidth  = Units.mm(Units.inches(Units.HOScale( 6 )))
    @property
    def __PlatformStairLanding(self):
        return self.__StairHeadRoom
    @property
    def __PlatformStairTotalRise(self):
        return self.__PlatformRoofHeight-\
                self.__PlatformHeight+(2*self.__PlatformRoofThickness)
    __ParapetWallHeight = Units.mm(Units.HOScale(18))
    @property
    def __KneeWallHeight(self):
        return(Units.mm(Units.HOScale(18))+self.__PlatformRoofThickness)
    __WindowHeight = Units.mm(Units.HOScale(Units.inches(8.5)))
    __WindowWidth  = Units.mm(Units.HOScale(Units.inches(6.5)))
    __WindowPostWidth = Units.mm(Units.HOScale(Units.inches(1)))
    __VestibleWidth   = Units.mm(Units.HOScale(Units.inches(10)))
    __VestibleHeight  = Units.mm(Units.HOScale(Units.inches(9)))
    __VestibleLength  = Units.mm(Units.HOScale(Units.inches(6)))
    __StairsColor  = tuple([0xaa/255.0,0xaa/255.0,0xaa/255.0])
    __FloorColor   = (.5,.5,.5)
    __BrickWallColor = (139.0/255.0,  26.0/255.0,  26.0/255.0)
    __InnerWallColor = (1.0, 1.0, 1.0)
    __RoofColor      = (0.0, 0.0, 0.0)
    def __TotalStairLength(self,height,landing):
        landings = math.floor(height / self.__StairLandingRiseMax)
        return (height*self.__StairRiseRatio)+(landings*landing)
    def __makeStairs(self,origin,height,width,extraLanding=0):
        z=0
        lastLanding = 0
        length=self.__TotalStairLength(height,width)+extraLanding
        
        x = 0
        stair = None
        while z < height and x < length:
            r = self.__StairRiser
            if z+r > height:
                r = height-z
            tread = self.__StairTread
            treadLength = length-x
            step = Part.makePlane(treadLength,width,origin.add(Base.Vector(x,0,z)))\
                    .extrude(Base.Vector(0,0,r))
            if stair == None:
                stair = step
            else:
                stair = stair.fuse(step)
            z = z+r
            if z >= lastLanding+self.__StairLandingRiseMax:
                x = x+ width
                lastLanding = z
            else:
                x = x+tread
        self.AddPart("Stairs_%.4fx%.4f"%(width,height))
        return stair
    def __makeStairsRev(self,origin,height,width,extraLanding=0):
        z=0
        lastLanding = 0
        length=self.__TotalStairLength(height,width)+extraLanding
        
        x = 0
        stair = None
        while z < height and x < length:
            r = self.__StairRiser
            if z+r > height:
                r = height-z
            tread = self.__StairTread
            treadLength = length-x
            step = Part.makePlane(treadLength,width,origin.add(Base.Vector(0,0,z)))\
                    .extrude(Base.Vector(0,0,r))
            if stair == None:
                stair = step
            else:
                stair = stair.fuse(step)
            z = z+r
            if z >= lastLanding+self.__StairLandingRiseMax:
                x = x+ width
                lastLanding = z
            else:
                x = x+tread
        self.AddPart("Stairs_%.4fx%.4f"%(width,height))
        return stair
    __DoorCutHeight = Units.mm(.98)
    __SingleDoorCutWidth = Units.mm(.46)
    __DoubleDoorCutWidth = Units.mm(.875)
    def __doubleDoorCut(self,origin,DeltaX):
        doorCut = Part.makePlane(self.__DoorCutHeight,self.__DoubleDoorCutWidth,
                                 origin.add(
                                    Base.Vector(0,self.__DoubleDoorCutWidth,0)),
                                 Base.Vector(1,0,0)
               ).extrude(Base.Vector(DeltaX,0,0))
        self.doorCut = doorCut
        return doorCut
    def __singleDoorCut(self,origin,DeltaX):
        doorCut = Part.makePlane(self.__DoorCutHeight,self.__SingleDoorCutWidth,
                                 origin.add(
                                    Base.Vector(0,self.__SingleDoorCutWidth,0)),
                                 Base.Vector(1,0,0)
               ).extrude(Base.Vector(DeltaX,0,0))
        self.doorCut = doorCut
        return doorCut
    def __init__(self,name,origin):
        LaserCut.LaserCut.SetPrefix("OverStation")
        self.name = name
        if not isinstance(origin,Base.Vector):
            raise RuntimeError("origin is not a Vector!")
        self.origin = origin
        platformStairLen = self.__TotalStairLength(
                                    self.__PlatformStairTotalRise,
                                    self.__PlatformStairWidth)
        #debug("*** UnderStation.__init__(): platformStairLen = %f",platformStairLen)
        self.platform1StairOrigin = origin.add(Base.Vector(
                                                    self.__TotalStationLength-\
                                                        self.__ShortPlatformLength,
                                                    self.__CombinedTrackAndPlatformWidth-\
                                                    self.__PlatformStairWidth,
                                                    self.__PlatformHeight))
        self.platform1Stair = self.__makeStairsRev(self.platform1StairOrigin,
                                       self.__PlatformStairTotalRise,
                                       self.__PlatformStairWidth)
        self.platform1StairRoofCut = Part.makePlane(
                                        self.__TotalStairLength(
                                            self.__PlatformStairTotalRise,
                                            self.__PlatformStairWidth),
                                        self.__PlatformStairWidth,
                                        self.platform1StairOrigin.add(
                                            Base.Vector(0,0,
                                                        self.__PlatformStairTotalRise-
                                                            (3*self.__MainWallWidth)))
               ).extrude(Base.Vector(0,0,self.__MainWallWidth*5))
        self.platform2StairOrigin = origin.add(Base.Vector(
                                                    self.__TotalStationLength-\
                                                        self.__ShortPlatformLength,
                                                    0,
                                                    self.__PlatformHeight))
        self.platform2Stair = self.__makeStairsRev(self.platform2StairOrigin,
                                       self.__PlatformStairTotalRise,
                                       self.__PlatformStairWidth)
        self.platform2StairRoofCut = Part.makePlane(
                                        self.__TotalStairLength(
                                            self.__PlatformStairTotalRise,
                                            self.__PlatformStairWidth),
                                        self.__PlatformStairWidth,
                                        self.platform2StairOrigin.add(
                                            Base.Vector(0,0,
                                                        self.__PlatformStairTotalRise-
                                                            (3*self.__MainWallWidth)))
               ).extrude(Base.Vector(0,0,self.__MainWallWidth*5))
        elevator1Origin = self.origin.add(Base.Vector(self.__ShortPlatformLength-(3*Elevator.ShaftLength),
                                        self.__CombinedTrackAndPlatformWidth-Elevator.ShaftLength,
                                        self.__PlatformHeight))
        self.platform1Elevator = Elevator(
            "Platform1Elevator",
            elevator1Origin,
            self.__PlatformStairTotalRise)
        self.AddPart("PlatformElevator")
        elevatorShelterOrigin = Base.Vector(elevator1Origin.x,
                                            elevator1Origin.y+Elevator.ShaftLength,
                                            origin.z+self.__PlatformHeight)
        elevatorShelter = Part.makePlane(self.__PlatformRoofHeight-self.__PlatformHeight,
                                         Elevator.ShaftLength,
                                         elevatorShelterOrigin.add(
                                            Base.Vector(
                                                Elevator.ShaftWidth+\
                                                self.__PlatformStairWidth,
                                                0,
                                                0)),
                                         Base.Vector(1,0,0))\
              .extrude(Base.Vector(-self.__GlassWallWidth,0,0))
        bb = elevatorShelter.BoundBox
        elevatorShelterDoorOrigin = Base.Vector(bb.XMin,
                                        bb.YMin+
                                            ((Elevator.ShaftLength-
                                              self.__SingleDoorCutWidth)/2),
                                        bb.ZMin)
        self.AddPiece(bb.YLength,bb.ZLength,".040 Clear Copolyester (SSC-104)")
        e1sA = Part.makePlane(self.__PlatformRoofHeight-self.__PlatformHeight,
                           self.__PlatformStairWidth,
                           elevatorShelterOrigin.add(
                            Base.Vector(
                                Elevator.ShaftWidth,
                                -Elevator.ShaftLength,
                                0)),
                           Base.Vector(0,1,0)).extrude(Base.Vector(0,self.__GlassWallWidth))
        elevatorShelter = elevatorShelter.cut(self.__singleDoorCut(elevatorShelterDoorOrigin,
                                             self.__GlassWallWidth))  
        self.elevator1Shelter = elevatorShelter.fuse(e1sA)
        LaserCut.CopolysterSSC_104Cut.AddCut(elevatorShelter)
        LaserCut.CopolysterSSC_104Cut.AddCut(e1sA)
        bb = e1sA.BoundBox
        self.AddPiece(bb.XLength,bb.ZLength,".040 Clear Copolyester (SSC-104)")
        self.AddPart("Tichy Train Group #8195 Single Glass Door")
        postSkip1 = (elevator1Origin.x,elevator1Origin.x+Elevator.ShaftWidth+self.__PlatformStairWidth)
        elevator2Origin = self.origin.add(Base.Vector(self.__ShortPlatformLength-(3*Elevator.ShaftLength),
                                        0,
                                        self.__PlatformHeight))
        self.platform2Elevator = Elevator(
            "Platform2Elevator",
            elevator2Origin,
            self.__PlatformStairTotalRise)
        self.AddPart("PlatformElevator")
        elevatorShelterOrigin = Base.Vector(elevator2Origin.x,
                                            elevator2Origin.y+Elevator.ShaftLength,
                                            origin.z+self.__PlatformHeight)
        elevatorShelter = Part.makePlane(self.__PlatformRoofHeight-self.__PlatformHeight,
                                         Elevator.ShaftLength,
                                         elevatorShelterOrigin.add(
                                            Base.Vector(
                                                Elevator.ShaftWidth+\
                                                self.__PlatformStairWidth,
                                                0,
                                                0)),
                                         Base.Vector(1,0,0))\
              .extrude(Base.Vector(-self.__GlassWallWidth,0,0))
        bb = elevatorShelter.BoundBox
        elevatorShelterDoorOrigin = Base.Vector(bb.XMin,
                                        bb.YMin+
                                            ((Elevator.ShaftLength-
                                              self.__SingleDoorCutWidth)/2),
                                        bb.ZMin)
        self.AddPiece(bb.YLength,bb.ZLength,".040 Clear Copolyester (SSC-104)")
        e2sA = Part.makePlane(self.__PlatformRoofHeight-self.__PlatformHeight,
                           self.__PlatformStairWidth,
                           elevatorShelterOrigin.add(
                            Base.Vector(
                                Elevator.ShaftWidth,
                                0,
                                0)),
                           Base.Vector(0,1,0)).extrude(Base.Vector(0,-self.__GlassWallWidth))
        elevatorShelter = elevatorShelter.cut(
            self.__singleDoorCut(elevatorShelterDoorOrigin,
                                 self.__GlassWallWidth))
        self.elevator2Shelter = elevatorShelter.fuse(e2sA)
        LaserCut.CopolysterSSC_104Cut.AddCut(elevatorShelter)
        LaserCut.CopolysterSSC_104Cut.AddCut(e2sA)
        bb = e2sA.BoundBox
        self.AddPiece(bb.XLength,bb.ZLength,".040 Clear Copolyester (SSC-104)")
        self.AddPart("Tichy Train Group #8195 Single Glass Door")
        platformBaseHeight = self.__PlatformHeight-Units.mm(Units.HOScale(12))
        platformBaseExtrude = Base.Vector(0,0,platformBaseHeight)
        platformBaseWidth = self.__PlatformWidth-Units.mm(Units.HOScale(12))
        p1borigin = origin.add(Base.Vector(
                                        0,
                                        self.__CombinedTrackAndPlatformWidth-\
                                            self.__PlatformWidth+\
                                            Units.mm(Units.HOScale(12)),
                                        0))
        platform = Part.makePlane(self.__LongPlatformLength,
                                  platformBaseWidth,
                                  p1borigin)\
                 .extrude(platformBaseExtrude)
        bb = platform.BoundBox
        self.AddPiece(bb.XLength,bb.YLength,"%.3fin Wood Block"%(platformBaseHeight/25.4))
        platformTopExtrude = Base.Vector(0,0,Units.mm(Units.HOScale(12)))
        p1origin = origin.add(Base.Vector(
                                0,
                                self.__CombinedTrackAndPlatformWidth-\
                                    self.__PlatformWidth,
                                self.__PlatformHeight-\
                                    Units.mm(Units.HOScale(12))))
        platform = platform.fuse(
            Part.makePlane(self.__LongPlatformLength,
                           self.__PlatformWidth,
                           p1origin)\
                 .extrude(platformTopExtrude))
        self.platform1 = platform
        stairShelterOrigin = Base.Vector(self.platform1StairOrigin.x,
                                                    self.platform1StairOrigin.y+\
                                                        self.__PlatformStairWidth,
                                                    origin.z+self.__PlatformHeight)
        self.stairShelterOrigin1 = stairShelterOrigin
        stairShelter = Part.makePlane(
                self.__PlatformRoofHeight-self.__PlatformHeight,
                self.__TotalStairLength(self.__PlatformStairTotalRise,
                                        self.__PlatformStairWidth)+
                self.__PlatformStairWidth,
                stairShelterOrigin.add(Base.Vector(-self.__GlassWallWidth,
                                                   -self.__PlatformStairWidth,0)),
                Base.Vector(0,1,0)).extrude(Base.Vector(0,-self.__GlassWallWidth,0))
        bb = stairShelter.BoundBox
        self.AddPiece(bb.XLength,bb.ZLength,".040 Clear Copolyester (SSC-104)")
        ss1A = Part.makePlane(self.__PlatformRoofHeight-self.__PlatformHeight,
                                      self.__PlatformStairWidth+
                                        self.__GlassWallWidth,
                                      stairShelterOrigin.add(
                                        Base.Vector(
                                            self.__TotalStairLength(
                                                self.__PlatformStairTotalRise,
                                                self.__PlatformStairWidth)+
                                            self.__PlatformStairWidth-
                                                self.__GlassWallWidth,
                                            0,0)),
                                      Base.Vector(1,0,0))\
               .extrude(Base.Vector(self.__GlassWallWidth,0,0))
        bb = ss1A.BoundBox
        stairShelterDoorOrigin = Base.Vector(bb.XMin,
                                             bb.YMin+
                                                ((self.__PlatformStairWidth-
                                                    self.__SingleDoorCutWidth)/2),
                                             bb.ZMin)
        ss1A = ss1A.cut(
            self.__singleDoorCut(stairShelterDoorOrigin,
                                 self.__GlassWallWidth))
        self.stair1Shelter = stairShelter.fuse(ss1A)
        LaserCut.CopolysterSSC_104Cut.AddCut(stairShelter)
        LaserCut.CopolysterSSC_104Cut.AddCut(ss1A)
        self.AddPiece(bb.YLength,bb.ZLength,".040 Clear Copolyester (SSC-104)")
        self.AddPart("Tichy Train Group #8195 Single Glass Door")
        stairShelterOrigin = Base.Vector(self.platform2StairOrigin.x,
                                                    self.platform2StairOrigin.y+\
                                                        self.__PlatformStairWidth,
                                                    origin.z+self.__PlatformHeight)
        self.stairShelterOrigin2 = stairShelterOrigin
        stairShelter = Part.makePlane(
                self.__PlatformRoofHeight-self.__PlatformHeight,
                self.__TotalStairLength(self.__PlatformStairTotalRise,
                                        self.__PlatformStairWidth)+
                self.__PlatformStairWidth,
                stairShelterOrigin.add(Base.Vector(-self.__GlassWallWidth,
                                                   self.__GlassWallWidth,0)),
                Base.Vector(0,1,0)).extrude(Base.Vector(0,-self.__GlassWallWidth,0))
        bb = stairShelter.BoundBox
        self.AddPiece(bb.XLength,bb.ZLength,".040 Clear Copolyester (SSC-104)")
        ss1A = Part.makePlane(self.__PlatformRoofHeight-self.__PlatformHeight,
                                      self.__PlatformStairWidth+
                                        self.__GlassWallWidth,
                                      stairShelterOrigin.add(
                                        Base.Vector(
                                            self.__TotalStairLength(
                                                self.__PlatformStairTotalRise,
                                                self.__PlatformStairWidth)+
                                            self.__PlatformStairWidth-
                                                self.__GlassWallWidth,
                                            self.__GlassWallWidth,0)),
                                      Base.Vector(1,0,0))\
               .extrude(Base.Vector(self.__GlassWallWidth,0,0))
        bb = ss1A.BoundBox
        self.AddPiece(bb.YLength,bb.ZLength,".040 Clear Copolyester (SSC-104)")
        stairShelterDoorOrigin = Base.Vector(bb.XMin,
                                             bb.YMin+
                                                ((self.__PlatformStairWidth-
                                                    self.__SingleDoorCutWidth)/2),
                                             bb.ZMin)
        ss1A = ss1A.cut(
            self.__singleDoorCut(stairShelterDoorOrigin,
                                 self.__GlassWallWidth))
        self.stair2Shelter = stairShelter.fuse(ss1A)
        LaserCut.CopolysterSSC_104Cut.AddCut(stairShelter)
        LaserCut.CopolysterSSC_104Cut.AddCut(ss1A)
        self.AddPart("Tichy Train Group #8195 Single Glass Door")
        platform = Part.makePlane(self.__LongPlatformLength,
                                  platformBaseWidth,
                                  origin)\
                 .extrude(platformBaseExtrude)
        bb = platform.BoundBox
        self.AddPiece(bb.XLength,bb.YLength,"%.3fin Wood Block"%(platformBaseHeight/25.4))
        platform = platform.fuse(
            Part.makePlane(self.__LongPlatformLength,
                           self.__PlatformWidth,
                           origin.add(
                            Base.Vector(
                                0,
                                0,
                                self.__PlatformHeight-\
                                    Units.mm(Units.HOScale(12)))))\
                 .extrude(platformTopExtrude))
        self.platform2 = platform
        p1RoofOrigin = Base.Vector(p1origin.x,p1origin.y,
                                   origin.z+self.__PlatformRoofHeight)
        p1roof = Part.makePlane(self.__LongPlatformLength,
                                self.__PlatformWidth,
                                p1RoofOrigin).extrude(Base.Vector(0,0,self.__PlatformRoofThickness))
        self.platform1 = self.platform1.fuse(p1roof
                   ).cut(self.platform1Elevator.shaft
                        ).cut(self.platform1StairRoofCut)
        p2RoofOrigin = Base.Vector(origin.x,origin.y,
                                   origin.z+self.__PlatformRoofHeight)
        p2roof = Part.makePlane(self.__LongPlatformLength,
                                self.__PlatformWidth,
                                p2RoofOrigin).extrude(Base.Vector(0,0,self.__PlatformRoofThickness))
        self.platform2 = self.platform2.fuse(p2roof
                    ).cut(self.platform2Elevator.shaft
                        ).cut(self.platform2StairRoofCut)
        postEnd = p1origin.x+self.__LongPlatformLength
        postX = p1origin.x+self.__PostOffset-self.__PostSpacing
        postLength = p1RoofOrigin.z-p1origin.z-Units.mm(Units.HOScale(12))
        while postX < postEnd-self.__PostSpacing:
            postX = postX + self.__PostSpacing
            #debug("*** postX = %f, postEnd is %f",postX,postEnd)
            if postX+self.__PostDiameter/2 > postSkip1[0] and \
               postX-self.__PostDiameter/2 < postSkip1[1]:
                continue
            post1Orig = Base.Vector(postX,p1origin.y+self.__PlatformWidth/2,origin.z+self.__PlatformHeight)
            post1 = Part.makeCylinder(self.__PostDiameter/2,postLength,post1Orig)
            self.platform1 = self.platform1.fuse(post1)
            post2Orig = Base.Vector(postX,origin.y+self.__PlatformWidth/2,origin.z+self.__PlatformHeight)
            post2 = Part.makeCylinder(self.__PostDiameter/2,postLength,post2Orig)
            self.platform2 = self.platform2.fuse(post2)
        self.AddPart("Walthers Cornerstone Part # 933-3175")
        ## Station proper
        floor1 = Part.makePlane(self.__BridgeWidth,
                                self.__CombinedTrackAndPlatformWidth,
                                elevator2Origin.add(
                                    Base.Vector(Elevator.ShaftWidth,
                                                0,
                                                self.__PlatformRoofHeight+
                                                    self.__PlatformRoofThickness-
                                                    self.__PlatformHeight))
               ).extrude(Base.Vector(0,0,self.__PlatformRoofThickness))
        bb = floor1.BoundBox
        self.AddPiece(bb.XLength,bb.YLength,".080 Styreen (SSS-10824)")
        stationOrigin = elevator2Origin.add(
                            Base.Vector(self.__MainStationXOffset,
                                        self.__CombinedTrackAndPlatformWidth,
                                        self.__PlatformRoofHeight+
                                             self.__PlatformRoofThickness-
                                             self.__PlatformHeight))
        floor2 = Part.makePlane(self.__MainStationWidth,
                                self.__MainStationLength,
                                stationOrigin
               ).extrude(Base.Vector(0,0,self.__PlatformRoofThickness))
        self.floor = floor1.fuse(floor2)
        ##bb = floor2.BoundBox
        ##self.AddPiece(bb.XLength,bb.YLength,".080 Styreen (SSS-10824)")
        wallLength_y = self.__CombinedTrackAndPlatformWidth#-(2*Elevator.ShaftLength)
        wallZOff = self.__PlatformRoofHeight+\
                        self.__PlatformRoofThickness-\
                        self.__PlatformHeight+\
                        self.__PlatformRoofThickness
        wall = Part.makePlane(self.__StationHeight,
                              wallLength_y,
                              elevator2Origin.add(
                                    Base.Vector(Elevator.ShaftWidth,
                                                #Elevator.ShaftLength+
                                                    wallLength_y,
                                                wallZOff)),
                              Base.Vector(1,0,0)
               ).extrude(Base.Vector(self.__GlassWallWidth,0,0))
        bb = wall.BoundBox
        self.AddPiece(bb.YLength,bb.ZLength,".040 Clear Copolyester (SSC-104)")
        LaserCut.CopolysterSSC_104Cut.AddCut(wall)
        wall1 = Part.makePlane(self.__StationHeight,
                               self.__CombinedTrackAndPlatformWidth-
                                (2*self.__PlatformStairWidth),
                               elevator2Origin.add(
                                Base.Vector(Elevator.ShaftWidth+
                                                self.__BridgeWidth-
                                                self.__GlassWallWidth,
                                            self.__CombinedTrackAndPlatformWidth-
                                                self.__PlatformStairWidth,
                                            wallZOff)),
                               Base.Vector(1,0,0)
                ).extrude(Base.Vector(self.__GlassWallWidth,0,0))
        bb = wall1.BoundBox
        self.AddPiece(bb.YLength,bb.ZLength,".040 Clear Copolyester (SSC-104)")
        LaserCut.CopolysterSSC_104Cut.AddCut(wall1)
        wall = wall.fuse(wall1)
        wall1 = Part.makePlane(self.__StationHeight+
                                    self.__PlatformRoofThickness,
                               self.__TotalStairLength(
                                    self.__PlatformStairTotalRise,
                                    self.__PlatformStairWidth)+
                                    self.__MainWallWidth,
                               self.stairShelterOrigin1.add(
                                Base.Vector(0,
                                            -self.__PlatformStairWidth-
                                                self.__MainWallWidth-.88,
                                            wallZOff-
                                                self.__PlatformRoofThickness)),
                               Base.Vector(0,1,0)
                ).extrude(Base.Vector(0,self.__GlassWallWidth,0))
        bb = wall1.BoundBox
        self.AddPiece(bb.XLength,bb.ZLength,".040 Clear Copolyester (SSC-104)")
        LaserCut.CopolysterSSC_104Cut.AddCut(wall1)
        wall = wall.fuse(wall1)
        wall1 = Part.makePlane(self.__StationHeight+
                                    self.__PlatformRoofThickness,
                               self.__PlatformStairWidth+self.__MainWallWidth+
                                    .88,
                               self.stairShelterOrigin1.add(
                                Base.Vector(
                                    self.__TotalStairLength(
                                        self.__PlatformStairTotalRise,
                                        self.__PlatformStairWidth)+
                                        self.__MainWallWidth,
                                    0,wallZOff-
                                        self.__PlatformRoofThickness)),
                               Base.Vector(1,0,0)
               ).extrude(Base.Vector(self.__GlassWallWidth,0,0))
        bb = wall1.BoundBox
        self.AddPiece(bb.YLength,bb.ZLength,".040 Clear Copolyester (SSC-104)")
        LaserCut.CopolysterSSC_104Cut.AddCut(wall1) 
        wall = wall.fuse(wall1) 
        wall1 = Part.makePlane(self.__StationHeight+
                                    self.__PlatformRoofThickness,
                               self.__TotalStairLength(
                                    self.__PlatformStairTotalRise,
                                    self.__PlatformStairWidth)+
                                        self.__MainWallWidth,
                               self.stairShelterOrigin2.add(
                                Base.Vector(self.__GlassWallWidth,
                                            self.__MainWallWidth,
                                            wallZOff-
                                                self.__PlatformRoofThickness)),
                               Base.Vector(0,1,0)
                ).extrude(Base.Vector(0,self.__GlassWallWidth,0))
        bb = wall1.BoundBox
        self.AddPiece(bb.XLength,bb.ZLength,".040 Clear Copolyester (SSC-104)")
        LaserCut.CopolysterSSC_104Cut.AddCut(wall1)
        wall = wall.fuse(wall1)
        wall1 = Part.makePlane(self.__StationHeight+
                                    self.__PlatformRoofThickness,
                               self.__PlatformStairWidth+
                                self.__MainWallWidth,
                               self.stairShelterOrigin2.add(
                                Base.Vector(
                                    self.__TotalStairLength(
                                        self.__PlatformStairTotalRise,
                                        self.__PlatformStairWidth)+
                                            self.__MainWallWidth,
                                    self.__MainWallWidth,wallZOff-
                                        self.__PlatformRoofThickness)),
                               Base.Vector(1,0,0)
               ).extrude(Base.Vector(self.__GlassWallWidth,0,0))
        bb = wall1.BoundBox
        self.AddPiece(bb.YLength,bb.ZLength,".040 Clear Copolyester (SSC-104)")
        LaserCut.CopolysterSSC_104Cut.AddCut(wall1)
        wall = wall.fuse(wall1) 
        wall1 = Part.makePlane(self.__StationHeight,
                               self.__MainStationLength,
                               stationOrigin.add(
                                Base.Vector(0,self.__MainStationLength,
                                            self.__PlatformRoofThickness)),
                               Base.Vector(1,0,0)
                   ).extrude(Base.Vector(self.__GlassWallWidth,0,0))
        bb = wall1.BoundBox
        doorOrigin = Base.Vector(bb.XMin,
                                 bb.YMin+
                                    ((bb.YLength-self.__DoubleDoorCutWidth)/2),
                                 bb.ZMin)
        wall1 = wall1.cut(self.__doubleDoorCut(doorOrigin,
                                               self.__GlassWallWidth))
        self.AddPart("Tichy Train Group #8198 Double Glass Door")
        self.AddPiece(bb.YLength,bb.ZLength,".040 Clear Copolyester (SSC-104)")
        LaserCut.CopolysterSSC_104Cut.AddCut(wall1)
        wall = wall.fuse(wall1)
        wall1 = Part.makePlane(self.__StationHeight,
                               self.__MainStationLength,
                               stationOrigin.add(
                                Base.Vector(self.__MainStationWidth-
                                                self.__GlassWallWidth,
                                            self.__MainStationLength,
                                            self.__PlatformRoofThickness)),
                               Base.Vector(1,0,0)
                   ).extrude(Base.Vector(self.__GlassWallWidth,0,0))
        bb = wall1.BoundBox
        doorOrigin = Base.Vector(bb.XMin,
                                 bb.YMin+
                                    ((bb.YLength-self.__DoubleDoorCutWidth)/2),
                                 bb.ZMin)
        wall1 = wall1.cut(self.__doubleDoorCut(doorOrigin,
                                               self.__GlassWallWidth))
        self.AddPart("Tichy Train Group #8198 Double Glass Door")
        self.AddPiece(bb.YLength,bb.ZLength,".040 Clear Copolyester (SSC-104)")
        LaserCut.CopolysterSSC_104Cut.AddCut(wall1)
        wall = wall.fuse(wall1)
        self.wall = wall
        backwall = Part.makePlane(self.__StationHeight+
                                    self.__PlatformRoofThickness+
                                    self.__ParapetWallHeight,
                                  self.__MainStationWidth+
                                    (2*self.__PlastructPS_97Thick),
                                  stationOrigin.add(
                                    Base.Vector(-self.__PlastructPS_97Thick,
                                                self.__MainStationLength,
                                                0)),
                                  Base.Vector(0,1,0)
                   ).extrude(Base.Vector(0,self.__PlastructPS_97Thick,0))
        bb = backwall.BoundBox
        self.AddPiece(bb.XLength,bb.ZLength,"Plastruct HO Brick (PS-97)")
        maxwidth = bb.XLength/2
        cut = Part.makePlane(bb.ZLength,maxwidth,
                             Base.Vector(bb.XMin,bb.YMin,bb.ZMin),
                             Base.Vector(0,1,0)).extrude(
                                Base.Vector(0,self.__PlastructPS_97Thick,0))
        #self.backwallcut = cut
        w1 = backwall.cut(cut)
        self.w1 = w1
        w2 = backwall.cut(w1)
        self.w2 = w2
        LaserCut.BricksPS_97Cut.AddCut(w1,-1,False)
        LaserCut.BricksPS_97Cut.AddCut(cut,-1,False)
        leftwall = Part.makePlane(self.__StationHeight+
                                    self.__PlatformRoofThickness+
                                    self.__ParapetWallHeight,
                                  self.__MainStationLength+
                                    (2*self.__PlastructPS_97Thick),
                                  stationOrigin.add(
                                    Base.Vector(-self.__PlastructPS_97Thick,
                                                self.__MainStationLength+
                                                    self.__PlastructPS_97Thick,
                                                0)),
                                  Base.Vector(1,0,0)
                  ).extrude(Base.Vector(self.__PlastructPS_97Thick,0,0))
        bb = leftwall.BoundBox
        self.AddPiece(bb.YLength,bb.ZLength,"Plastruct HO Brick (PS-97)")
        vestibleOrigin = Base.Vector(bb.XMin,
                                     bb.YMin+
                                        ((bb.YLength-self.__VestibleWidth)/2),
                                     bb.ZMin)
        vestibleCutOrigin = vestibleOrigin.add(
            Base.Vector(0,self.__VestibleWidth,0))
        leftwall = leftwall.cut(
            Part.makePlane(self.__VestibleHeight+self.__PlatformRoofThickness,
                           self.__VestibleWidth,
                           vestibleCutOrigin,
                           Base.Vector(1,0,0)).extrude(
                                Base.Vector(self.__PlastructPS_97Thick,0,0)))
        vestibleFloorOrigin = vestibleOrigin.add(
            Base.Vector(-self.__VestibleLength,0,0))
        vestibleFloor = Part.makePlane(self.__VestibleLength+
                                        self.__PlastructPS_97Thick,
                                       self.__VestibleWidth,
                                       vestibleFloorOrigin).extrude(
                                        Base.Vector(0,0,
                                                    self.__PlatformRoofThickness))
        self.floor = self.floor.fuse(vestibleFloor)
        self.vestibleCeilingLeft = Part.makePlane(self.__VestibleLength+
                                        self.__PlastructPS_97Thick,
                                       self.__VestibleWidth,
                                       vestibleFloorOrigin.add(
                                        Base.Vector(0,0,
                                                    self.__PlatformRoofThickness+
                                                        self.__VestibleHeight))
                        ).extrude(Base.Vector(0,0,
                                              self.__CeilingAndRoofThickness))
        bb1 = self.vestibleCeilingLeft.BoundBox                                              
        self.AddPiece(bb1.XLength,bb.YLength,".020 Styreen (SSS-10224)")
        LaserCut.StyreneSSS_10224Cut.AddCut(self.vestibleCeilingLeft)
        leftwall = leftwall.cut(vestibleFloor)
        windowOrigin = Base.Vector(bb.XMin,
                                   bb.YMin+self.__PlastructPS_97Thick+
                                    (self.__WindowPostWidth/2),
                                   bb.ZMin+self.__KneeWallHeight+
                                    self.__PlatformRoofThickness)
        yAdjust = Base.Vector(0,self.__WindowWidth,0)
        leftwall = leftwall.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        leftwall = leftwall.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__VestibleWidth+
                                          self.__WindowWidth+
                                          self.__WindowPostWidth,0))
        leftwall = leftwall.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        leftwall = leftwall.cut(
            Part.makePlane(self.__WindowHeight,
                           self.__WindowWidth,
                           windowOrigin.add(yAdjust),
                           Base.Vector(1,0,0)).extrude(
                                    Base.Vector(self.__PlastructPS_97Thick,
                                                0,0)))
        LaserCut.BricksPS_97Cut.AddCut(leftwall,1,False)
        vestibleInnerWall = Part.makePlane(self.__VestibleHeight,
                                           self.__VestibleLength+
                                            self.__PlastructPS_97Thick,
                                           vestibleFloorOrigin.add(
                                            Base.Vector(0,0,
                                                self.__PlatformRoofThickness)),
                                           Base.Vector(0,1,0)).extrude(
                                            Base.Vector(0,self.__MainWallWidth))
        bb = vestibleInnerWall.BoundBox
        self.AddPiece(bb.XLength,bb.ZLength,".080 Styreen (SSS-10824)")
        LaserCut.StyreneSSS_10824Cut.AddCut(vestibleInnerWall)
        self.vestibleInnerWallLeft = vestibleInnerWall
        vestibleInnerWall = Part.makePlane(self.__VestibleHeight,
                                           self.__VestibleLength+
                                            self.__PlastructPS_97Thick,
                                           vestibleFloorOrigin.add(
                                            Base.Vector(0,self.__VestibleWidth-
                                                        self.__MainWallWidth,
                                                self.__PlatformRoofThickness)),
                                           Base.Vector(0,1,0)).extrude(
                                            Base.Vector(0,self.__MainWallWidth))
        bb = vestibleInnerWall.BoundBox
        LaserCut.StyreneSSS_10824Cut.AddCut(vestibleInnerWall)
        self.AddPiece(bb.XLength,bb.ZLength,".080 Styreen (SSS-10824)")
        self.vestibleInnerWallLeft = self.vestibleInnerWallLeft.fuse(vestibleInnerWall)
        vestibleInnerWall = Part.makePlane(self.__VestibleHeight,
                                           self.__VestibleWidth-
                                            (2*self.__MainWallWidth),
                                           vestibleFloorOrigin.add(
                                            Base.Vector(0,self.__VestibleWidth-
                                                            self.__MainWallWidth,
                                                        self.__PlatformRoofThickness)),
                                           Base.Vector(1,0,0)).extrude(
                                            Base.Vector(self.__MainWallWidth,0,0))
        bb = vestibleInnerWall.BoundBox
        self.AddPiece(bb.YLength,bb.ZLength,".080 Styreen (SSS-10824)")
        vestibleInnerWall = vestibleInnerWall.cut(
            self.__doubleDoorCut(Base.Vector(bb.XMin,
                                             bb.YMin+.44+
                                                ((bb.YLength-self.__DoubleDoorCutWidth)/2),
                                             bb.ZMin),
                                 self.__MainWallWidth))
        LaserCut.StyreneSSS_10824Cut.AddCut(vestibleInnerWall)
        self.AddPart("Tichy Train Group #8198 Double Glass Door")
        self.vestibleInnerWallLeft = self.vestibleInnerWallLeft.fuse(vestibleInnerWall)
        vestibleOuterWall = Part.makePlane(self.__VestibleHeight+
                                            self.__ParapetWallHeight+
                                            self.__PlatformRoofThickness,
                                           self.__VestibleLength+
                                            self.__PlastructPS_97Thick,
                                           vestibleFloorOrigin.add(
                                            Base.Vector(
                                                -self.__PlastructPS_97Thick,
                                                -self.__PlastructPS_97Thick,
                                                0)),
                                           Base.Vector(0,1,0)).extrude(
                                            Base.Vector(0,self.__PlastructPS_97Thick,0))
        bb = vestibleOuterWall.BoundBox
        self.AddPiece(bb.XLength,bb.ZLength,"Plastruct HO Brick (PS-97)")
        LaserCut.BricksPS_97Cut.AddCut(vestibleOuterWall,1,False)
        vestibleOuterWallLeft = vestibleOuterWall
        vestibleOuterWall = Part.makePlane(self.__VestibleHeight+
                                            self.__ParapetWallHeight+
                                            self.__PlatformRoofThickness,
                                           self.__VestibleLength+
                                            self.__PlastructPS_97Thick,
                                           vestibleFloorOrigin.add(
                                            Base.Vector(
                                                -self.__PlastructPS_97Thick,
                                                self.__VestibleWidth,
                                                0)),
                                           Base.Vector(0,1,0)).extrude(
                                            Base.Vector(0,self.__PlastructPS_97Thick,0))
        bb = vestibleOuterWall.BoundBox
        self.AddPiece(bb.XLength,bb.ZLength,"Plastruct HO Brick (PS-97)")
        LaserCut.BricksPS_97Cut.AddCut(vestibleOuterWall,-1,False)
        vestibleOuterWallLeft = vestibleOuterWallLeft.fuse(vestibleOuterWall)
        vestibleOuterWall = Part.makePlane(self.__VestibleHeight+
                                            self.__ParapetWallHeight+
                                            self.__PlatformRoofThickness,
                                           self.__VestibleWidth+
                                            (2*self.__PlastructPS_97Thick),
                                           vestibleFloorOrigin.add(
                                            Base.Vector(
                                                -self.__PlastructPS_97Thick,
                                                self.__VestibleWidth+
                                                    self.__PlastructPS_97Thick,
                                                0)),
                                           Base.Vector(1,0,0)).extrude(
                                            Base.Vector(self.__PlastructPS_97Thick,0,0))
        bb = vestibleOuterWall.BoundBox
        self.AddPiece(bb.YLength,bb.ZLength,"Plastruct HO Brick (PS-97)")
        vestibleOuterWall = vestibleOuterWall.cut(
            self.__doubleDoorCut(Base.Vector(bb.XMin,
                                             bb.YMin+.44+
                                                ((bb.YLength-self.__DoubleDoorCutWidth)/2),
                                             bb.ZMin+
                                                self.__PlatformRoofThickness),
                                 self.__PlastructPS_97Thick))
        LaserCut.BricksPS_97Cut.AddCut(vestibleOuterWall,1,False) 
        vestibleOuterWallLeft = vestibleOuterWallLeft.fuse(vestibleOuterWall)
        rightwall = Part.makePlane(self.__StationHeight+
                                    self.__PlatformRoofThickness+
                                    self.__ParapetWallHeight,
                                  self.__MainStationLength+
                                    (2*self.__PlastructPS_97Thick),
                                  stationOrigin.add(
                                    Base.Vector(self.__MainStationWidth,
                                                self.__MainStationLength+
                                                    self.__PlastructPS_97Thick,
                                                0)),
                                  Base.Vector(1,0,0)
                  ).extrude(Base.Vector(self.__PlastructPS_97Thick,0,0))
        bb = rightwall.BoundBox
        self.AddPiece(bb.YLength,bb.ZLength,"Plastruct HO Brick (PS-97)")
        vestibleOrigin = Base.Vector(bb.XMin,
                                     bb.YMin+
                                        ((bb.YLength-self.__VestibleWidth)/2),
                                     bb.ZMin)
        vestibleCutOrigin = vestibleOrigin.add(
            Base.Vector(0,self.__VestibleWidth,0))
        rightwall = rightwall.cut(
            Part.makePlane(self.__VestibleHeight+self.__PlatformRoofThickness,
                           self.__VestibleWidth,
                           vestibleCutOrigin,
                           Base.Vector(1,0,0)).extrude(
                                Base.Vector(self.__PlastructPS_97Thick,0,0)))
        vestibleFloorOrigin = vestibleOrigin
        vestibleFloor = Part.makePlane(self.__VestibleLength+
                                        self.__PlastructPS_97Thick,
                                       self.__VestibleWidth,
                                       vestibleFloorOrigin).extrude(
                                        Base.Vector(0,0,
                                                    self.__PlatformRoofThickness))
        self.floor = self.floor.fuse(vestibleFloor)
        self.vestibleCeilingRight = Part.makePlane(self.__VestibleLength+
                                        self.__PlastructPS_97Thick,
                                       self.__VestibleWidth,
                                       vestibleFloorOrigin.add(
                                        Base.Vector(0,0,
                                                    self.__PlatformRoofThickness+
                                                        self.__VestibleHeight))
                        ).extrude(Base.Vector(0,0,
                                              self.__CeilingAndRoofThickness))
        bb1 = self.vestibleCeilingRight.BoundBox                                              
        self.AddPiece(bb1.XLength,bb.YLength,".020 Styreen (SSS-10224)")
        LaserCut.StyreneSSS_10224Cut.AddCut(self.vestibleCeilingRight)
        rightwall = rightwall.cut(vestibleFloor)
        windowOrigin = Base.Vector(bb.XMin,
                                   bb.YMin+self.__PlastructPS_97Thick+
                                    (self.__WindowPostWidth/2),
                                   bb.ZMin+self.__KneeWallHeight+
                                    self.__PlatformRoofThickness)
        rightwall = rightwall.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        rightwall = rightwall.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__VestibleWidth+
                                          self.__WindowWidth+
                                          self.__WindowPostWidth,0))
        rightwall = rightwall.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        rightwall = rightwall.cut(
            Part.makePlane(self.__WindowHeight,
                           self.__WindowWidth,
                           windowOrigin.add(yAdjust),
                           Base.Vector(1,0,0)).extrude(
                                    Base.Vector(self.__PlastructPS_97Thick,
                                                0,0)))
        self.AddPiece(bb.YLength,bb.ZLength,"Plastruct HO Brick (PS-97)")
        LaserCut.BricksPS_97Cut.AddCut(rightwall,-1,False)
        vestibleInnerWall = Part.makePlane(self.__VestibleHeight,
                                           self.__VestibleLength+
                                            self.__PlastructPS_97Thick,
                                           vestibleFloorOrigin.add(
                                            Base.Vector(0,0,
                                                self.__PlatformRoofThickness)),
                                           Base.Vector(0,1,0)).extrude(
                                            Base.Vector(0,self.__MainWallWidth))
        bb = vestibleInnerWall.BoundBox
        self.AddPiece(bb.XLength,bb.ZLength,".080 Styreen (SSS-10824)")
        LaserCut.StyreneSSS_10824Cut.AddCut(vestibleInnerWall)
        self.vestibleInnerWallRight = vestibleInnerWall
        vestibleInnerWall = Part.makePlane(self.__VestibleHeight,
                                           self.__VestibleLength+
                                            self.__PlastructPS_97Thick,
                                           vestibleFloorOrigin.add(
                                            Base.Vector(0,self.__VestibleWidth-
                                                        self.__MainWallWidth,
                                                self.__PlatformRoofThickness)),
                                           Base.Vector(0,1,0)).extrude(
                                            Base.Vector(0,self.__MainWallWidth))
        bb = vestibleInnerWall.BoundBox
        self.AddPiece(bb.XLength,bb.ZLength,".080 Styreen (SSS-10824)")
        LaserCut.StyreneSSS_10824Cut.AddCut(vestibleInnerWall)
        self.vestibleInnerWallRight = self.vestibleInnerWallRight.fuse(vestibleInnerWall)
        vestibleInnerWall = Part.makePlane(self.__VestibleHeight,
                                           self.__VestibleWidth-
                                            (2*self.__MainWallWidth),
                                           vestibleFloorOrigin.add(
                                            Base.Vector(self.__VestibleLength+
                                                            self.__PlastructPS_97Thick-
                                                            self.__MainWallWidth,
                                                        self.__VestibleWidth-
                                                            self.__MainWallWidth,
                                                        self.__PlatformRoofThickness)),
                                           Base.Vector(1,0,0)).extrude(
                                            Base.Vector(self.__MainWallWidth,0,0))
        bb = vestibleInnerWall.BoundBox
        self.AddPiece(bb.YLength,bb.ZLength,".080 Styreen (SSS-10824)")
        vestibleInnerWall = vestibleInnerWall.cut(
            self.__doubleDoorCut(Base.Vector(bb.XMin,
                                             bb.YMin+.43+
                                                ((bb.YLength-self.__DoubleDoorCutWidth)/2),
                                             bb.ZMin),
                                 self.__MainWallWidth))
        LaserCut.StyreneSSS_10824Cut.AddCut(vestibleInnerWall)
        self.AddPart("Tichy Train Group #8198 Double Glass Door")
        self.vestibleInnerWallRight = self.vestibleInnerWallRight.fuse(vestibleInnerWall)
        vestibleOuterWall = Part.makePlane(self.__VestibleHeight+
                                            self.__ParapetWallHeight+
                                            self.__PlatformRoofThickness,
                                           self.__VestibleLength+
                                            self.__PlastructPS_97Thick,
                                           vestibleFloorOrigin.add(
                                            Base.Vector(
                                                self.__PlastructPS_97Thick,
                                                -self.__PlastructPS_97Thick,
                                                0)),
                                           Base.Vector(0,1,0)).extrude(
                                            Base.Vector(0,self.__PlastructPS_97Thick,0))
        bb = vestibleOuterWall.BoundBox
        self.AddPiece(bb.XLength,bb.ZLength,"Plastruct HO Brick (PS-97)")
        LaserCut.BricksPS_97Cut.AddCut(vestibleOuterWall,1,False)
        vestibleOuterWallRight = vestibleOuterWall
        vestibleOuterWall = Part.makePlane(self.__VestibleHeight+
                                            self.__ParapetWallHeight+
                                            self.__PlatformRoofThickness,
                                           self.__VestibleLength+
                                            self.__PlastructPS_97Thick,
                                           vestibleFloorOrigin.add(
                                            Base.Vector(
                                                self.__PlastructPS_97Thick,
                                                self.__VestibleWidth,
                                                0)),
                                           Base.Vector(0,1,0)).extrude(
                                            Base.Vector(0,self.__PlastructPS_97Thick,0))
        bb = vestibleOuterWall.BoundBox
        self.AddPiece(bb.XLength,bb.ZLength,"Plastruct HO Brick (PS-97)")
        LaserCut.BricksPS_97Cut.AddCut(vestibleOuterWall,-1,False)
        vestibleOuterWallRight = vestibleOuterWallRight.fuse(vestibleOuterWall)
        vestibleOuterWall = Part.makePlane(self.__VestibleHeight+
                                            self.__ParapetWallHeight+
                                            self.__PlatformRoofThickness,
                                           self.__VestibleWidth+
                                            (2*self.__PlastructPS_97Thick),
                                           vestibleFloorOrigin.add(
                                            Base.Vector(
                                                self.__VestibleLength+
                                                    self.__PlastructPS_97Thick,
                                                self.__VestibleWidth+
                                                    self.__PlastructPS_97Thick,
                                                0)),
                                           Base.Vector(1,0,0)).extrude(
                                            Base.Vector(self.__PlastructPS_97Thick,0,0))
        bb = vestibleOuterWall.BoundBox
        self.AddPiece(bb.YLength,bb.ZLength,"Plastruct HO Brick (PS-97)")
        vestibleOuterWall = vestibleOuterWall.cut(
            self.__doubleDoorCut(Base.Vector(bb.XMin,
                                             bb.YMin+.44+
                                                ((bb.YLength-self.__DoubleDoorCutWidth)/2),
                                             bb.ZMin+
                                                self.__PlatformRoofThickness),
                                 self.__PlastructPS_97Thick))
        LaserCut.BricksPS_97Cut.AddCut(vestibleOuterWall,-1,False)
        vestibleOuterWallRight = vestibleOuterWallRight.fuse(vestibleOuterWall)
        frontwall = Part.makePlane(self.__StationHeight+
                                    self.__PlatformRoofThickness+
                                    self.__ParapetWallHeight,
                                   (182.85-147.81)+
                                    self.__PlastructPS_97Thick,
                                   stationOrigin.add(
                                    Base.Vector(-self.__PlastructPS_97Thick,
                                                -self.__PlastructPS_97Thick,
                                                0)),
                                   Base.Vector(0,1,0)).extrude(Base.Vector(
                                    0,self.__PlastructPS_97Thick,0))
        bb = frontwall.BoundBox
        self.AddPiece(bb.XLength,bb.ZLength,"Plastruct HO Brick (PS-97)")
        LaserCut.BricksPS_97Cut.AddCut(frontwall,1,False)
        frontwall1 = Part.makePlane(self.__StationHeight+
                                        self.__PlatformRoofThickness+
                                        self.__ParapetWallHeight,
                                    3.29+self.__PlastructPS_97Thick,
                                    self.stairShelterOrigin1.add(
                                        Base.Vector(self.__TotalStairLength(
                                                        self.__PlatformStairTotalRise,
                                                        self.__PlatformStairWidth)+
                                                      self.__GlassWallWidth+
                                                      self.__MainWallWidth,
                                                    -self.__PlastructPS_97Thick,
                                                    wallZOff-self.__PlatformRoofThickness)),
                                    Base.Vector(0,1,0)).extrude(
                                        Base.Vector(0,self.__PlastructPS_97Thick,0))
        bb = frontwall1.BoundBox
        self.AddPiece(bb.XLength,bb.ZLength,"Plastruct HO Brick (PS-97)")
        LaserCut.BricksPS_97Cut.AddCut(frontwall1,1,False)
        frontwall = frontwall.fuse(frontwall1)
        temp = Part.makePlane(self.__StationHeight+5.84+
                                self.__PlatformRoofThickness+
                                self.__ParapetWallHeight,
                              Elevator.ShaftLength+
                                self.__PlastructPS_97Thick,
                              elevator1Origin.add(
                                Base.Vector(
                                    -self.__PlastructPS_97Thick,
                                    Elevator.ShaftLength,
                                    self.__PlatformRoofHeight+
                                        self.__PlatformRoofThickness-
                                        self.__PlatformHeight)),
                              Base.Vector(1,0,0)).extrude(
                                Base.Vector(self.__PlastructPS_97Thick,0,0))
        bb = temp.BoundBox
        self.AddPiece(bb.YLength,bb.ZLength,"Plastruct HO Brick (PS-97)")
        LaserCut.BricksPS_97Cut.AddCut(temp,1,False)
        leftbridgewall = temp
        temp = Part.makePlane(self.__StationHeight+5.84+
                                self.__PlatformRoofThickness+
                                self.__ParapetWallHeight,
                              Elevator.ShaftWidth+
                                self.__PlastructPS_97Thick,
                              elevator1Origin.add(
                                Base.Vector(
                                    -self.__PlastructPS_97Thick,
                                    -self.__PlastructPS_97Thick,
                                    self.__PlatformRoofHeight+
                                        self.__PlatformRoofThickness-
                                        self.__PlatformHeight)),
                              Base.Vector(0,1,0)).extrude(
                                Base.Vector(0,self.__PlastructPS_97Thick,0))
        bb = temp.BoundBox
        self.AddPiece(bb.XLength,bb.ZLength,"Plastruct HO Brick (PS-97)")
        LaserCut.BricksPS_97Cut.AddCut(temp,1,False)
        leftbridgewall = leftbridgewall.fuse(temp)
        bridgeWall_y = self.__CombinedTrackAndPlatformWidth - \
                    (2*Elevator.ShaftLength)
        temp = Part.makePlane(self.__StationHeight+
                                self.__PlatformRoofThickness+
                                self.__ParapetWallHeight,
                              bridgeWall_y,
                              elevator2Origin.add(
                                Base.Vector(
                                    Elevator.ShaftWidth-
                                        self.__PlastructPS_97Thick,
                                    Elevator.ShaftLength+bridgeWall_y,
                                    self.__PlatformRoofHeight+
                                        self.__PlatformRoofThickness-
                                        self.__PlatformHeight)),
                              Base.Vector(1,0,0)).extrude(
                                Base.Vector(self.__PlastructPS_97Thick,0,0))
        bb = temp.BoundBox
        self.AddPiece(bb.YLength,bb.ZLength,"Plastruct HO Brick (PS-97)")
        # windows
        windowOrigin = Base.Vector(bb.XMin,
                                   bb.YMin+self.__PlastructPS_97Thick+
                                    (self.__WindowPostWidth/2)+4.5,
                                   bb.ZMin+self.__KneeWallHeight+
                                    self.__PlatformRoofThickness)
        yAdjust = Base.Vector(0,self.__WindowWidth,0)
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        LaserCut.BricksPS_97Cut.AddCut(temp,1,False)
        leftbridgewall = leftbridgewall.fuse(temp)
        temp = Part.makePlane(self.__StationHeight+5.84+
                                self.__PlatformRoofThickness+
                                self.__ParapetWallHeight,
                              Elevator.ShaftWidth+
                                self.__PlastructPS_97Thick,
                              elevator2Origin.add(
                                Base.Vector(
                                    -self.__PlastructPS_97Thick,
                                    Elevator.ShaftLength,
                                    self.__PlatformRoofHeight+
                                        self.__PlatformRoofThickness-
                                        self.__PlatformHeight)),
                              Base.Vector(0,1,0)).extrude(
                                Base.Vector(0,self.__PlastructPS_97Thick,0))
        bb = temp.BoundBox
        self.AddPiece(bb.XLength,bb.ZLength,"Plastruct HO Brick (PS-97)")
        LaserCut.BricksPS_97Cut.AddCut(temp,1,False)
        leftbridgewall = leftbridgewall.fuse(temp)
        temp = Part.makePlane(self.__StationHeight+5.84+
                                self.__PlatformRoofThickness+
                                self.__ParapetWallHeight,
                              Elevator.ShaftLength+
                                self.__PlastructPS_97Thick,
                              elevator2Origin.add(
                                Base.Vector(
                                    -self.__PlastructPS_97Thick,
                                    Elevator.ShaftLength+
                                        self.__PlastructPS_97Thick,
                                    self.__PlatformRoofHeight+
                                        self.__PlatformRoofThickness-
                                        self.__PlatformHeight)),
                              Base.Vector(1,0,0)).extrude(
                                Base.Vector(self.__PlastructPS_97Thick,0,0))
        bb = temp.BoundBox
        self.AddPiece(bb.YLength,bb.ZLength,"Plastruct HO Brick (PS-97)")
        LaserCut.BricksPS_97Cut.AddCut(temp,1,False)
        leftbridgewall = leftbridgewall.fuse(temp)
        temp = Part.makePlane(self.__StationHeight+
                                self.__PlatformRoofThickness+
                                self.__ParapetWallHeight,
                              self.__PlatformStairWidth+
                                self.__PlastructPS_97Thick+
                                self.__MainWallWidth+.88,
                              self.stairShelterOrigin1.add(
                                Base.Vector(self.__TotalStairLength(
                                                self.__PlatformStairTotalRise,
                                                self.__PlatformStairWidth)+
                                                      self.__GlassWallWidth+
                                                      self.__MainWallWidth,
                                                    0,
                                                    wallZOff-
                                                        self.__PlatformRoofThickness)),
                                    Base.Vector(1,0,0)).extrude(
                                        Base.Vector(self.__PlastructPS_97Thick,
                                                    0,0))
        bb = temp.BoundBox
        self.AddPiece(bb.YLength,bb.ZLength,"Plastruct HO Brick (PS-97)")
        windowOrigin = Base.Vector(bb.XMin,
                                   bb.YMin+self.__PlastructPS_97Thick+
                                    (self.__WindowPostWidth/2)+.88,
                                   bb.ZMin+self.__KneeWallHeight+
                                    self.__PlatformRoofThickness)
        w_y = self.__PlatformStairWidth-self.__WindowPostWidth
        temp = temp.cut(
            Part.makePlane(self.__WindowHeight,
                           w_y,
                           windowOrigin.add(Base.Vector(0,w_y,0)),
                           Base.Vector(1,0,0)).extrude(
                            Base.Vector(self.__PlastructPS_97Thick,0,0)))
        LaserCut.BricksPS_97Cut.AddCut(temp,-1,False)
        rightbridgewall = temp
        temp = Part.makePlane(self.__StationHeight+
                                self.__PlatformRoofThickness+
                                self.__ParapetWallHeight,
                              self.__TotalStairLength(
                                self.__PlatformStairTotalRise,
                                self.__PlatformStairWidth)+
                                    self.__PlastructPS_97Thick+
                                    self.__GlassWallWidth+
                                    self.__MainWallWidth,
                              self.stairShelterOrigin1.add(
                                Base.Vector(0,
                                            -(self.__PlatformStairWidth+
                                              self.__PlastructPS_97Thick+
                                              self.__MainWallWidth+.88),
                                            wallZOff-
                                                self.__PlatformRoofThickness)),
                              Base.Vector(0,1,0)).extrude(
                                Base.Vector(0,self.__PlastructPS_97Thick,0))
        bb = temp.BoundBox
        self.AddPiece(bb.XLength,bb.ZLength,"Plastruct HO Brick (PS-97)")
        windowOrigin = Base.Vector(bb.XMin+self.__PlastructPS_97Thick+
                                    (self.__WindowPostWidth/2)+3.5,
                                   bb.YMin,
                                   bb.ZMin+self.__KneeWallHeight+
                                    self.__PlatformRoofThickness)
        temp = temp.cut(
            Part.makePlane(self.__WindowHeight,
                           self.__WindowWidth,
                           windowOrigin,
                           Base.Vector(0,1,0)).extrude(
                            Base.Vector(0,self.__PlastructPS_97Thick,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__PlastructPS_97Thick,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__PlastructPS_97Thick,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__PlastructPS_97Thick,0)))
        windowOrigin = windowOrigin.add(
                        Base.Vector(self.__WindowWidth+
                                        self.__WindowPostWidth,0,0))
        LaserCut.BricksPS_97Cut.AddCut(temp,1,False)
        rightbridgewall = rightbridgewall.fuse(temp)
        bridgeWall_y = self.__CombinedTrackAndPlatformWidth - \
                        (2*self.__PlatformStairWidth)-self.__GlassWallWidth-\
                        (2*self.__MainWallWidth)-.88
        temp = Part.makePlane(self.__StationHeight+
                                self.__PlatformRoofThickness+
                                self.__ParapetWallHeight,
                              bridgeWall_y,
                              self.stairShelterOrigin2.add(
                                Base.Vector(
                                    0,
                                    bridgeWall_y+self.__GlassWallWidth+
                                        self.__MainWallWidth,
                                    self.__PlatformRoofHeight+
                                        self.__PlatformRoofThickness-
                                        self.__PlatformHeight)),
                              Base.Vector(1,0,0)).extrude(
                                Base.Vector(self.__PlastructPS_97Thick,0,0))
        bb = temp.BoundBox
        self.AddPiece(bb.YLength,bb.ZLength,"Plastruct HO Brick (PS-97)")
        # windows
        windowOrigin = Base.Vector(bb.XMin,
                                   bb.YMin+self.__PlastructPS_97Thick+
                                    (self.__WindowPostWidth/2)+4.5+6.8+
                                    self.__MainWallWidth,
                                   bb.ZMin+self.__KneeWallHeight+
                                    self.__PlatformRoofThickness)
        yAdjust = Base.Vector(0,self.__WindowWidth,0)
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        windowOrigin = windowOrigin.add(
                            Base.Vector(0,self.__WindowWidth+
                                          self.__WindowPostWidth,0))
        temp = temp.cut(
            Part.makePlane(self.__WindowHeight,
                           self.__WindowWidth,
                           windowOrigin.add(yAdjust),
                           Base.Vector(1,0,0)).extrude(
                                    Base.Vector(self.__PlastructPS_97Thick,
                                                0,0)))
        LaserCut.BricksPS_97Cut.AddCut(temp,-1,False)
        rightbridgewall = rightbridgewall.fuse(temp)
        temp = Part.makePlane(self.__StationHeight+
                                self.__PlatformRoofThickness+
                                self.__ParapetWallHeight,
                              self.__TotalStairLength(
                                self.__PlatformStairTotalRise,
                                self.__PlatformStairWidth)+
                                    self.__PlastructPS_97Thick+
                                    self.__GlassWallWidth+
                                    self.__MainWallWidth,
                              self.stairShelterOrigin2.add(
                                Base.Vector(0,
                                            self.__GlassWallWidth+
                                                self.__MainWallWidth,
                                            wallZOff-
                                                self.__PlatformRoofThickness)),
                              Base.Vector(0,1,0)).extrude(
                                Base.Vector(0,self.__PlastructPS_97Thick,0))
        bb = temp.BoundBox
        self.AddPiece(bb.XLength,bb.ZLength,"Plastruct HO Brick (PS-97)")
        windowOrigin = Base.Vector(bb.XMin+self.__PlastructPS_97Thick+
                                    (self.__WindowPostWidth/2)+3.5,
                                   bb.YMin,
                                   bb.ZMin+self.__KneeWallHeight+
                                    self.__PlatformRoofThickness)
        temp = temp.cut(
            Part.makePlane(self.__WindowHeight,
                           self.__WindowWidth,
                           windowOrigin,
                           Base.Vector(0,1,0)).extrude(
                            Base.Vector(0,self.__PlastructPS_97Thick,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__PlastructPS_97Thick,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__PlastructPS_97Thick,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__PlastructPS_97Thick,0)))
        windowOrigin = windowOrigin.add(
                        Base.Vector(self.__WindowWidth+
                                        self.__WindowPostWidth,0,0))
        LaserCut.BricksPS_97Cut.AddCut(temp,-1,False)
        rightbridgewall = rightbridgewall.fuse(temp)
        temp = Part.makePlane(self.__StationHeight+
                                self.__PlatformRoofThickness+
                                self.__ParapetWallHeight,
                              self.__PlatformStairWidth+
                                self.__GlassWallWidth+
                                self.__PlastructPS_97Thick+
                                self.__MainWallWidth,
                              self.stairShelterOrigin2.add(
                                Base.Vector(self.__TotalStairLength(
                                                self.__PlatformStairTotalRise,
                                                self.__PlatformStairWidth)+
                                                    self.__GlassWallWidth+
                                                    self.__MainWallWidth,
                                             self.__GlassWallWidth+
                                                 self.__PlastructPS_97Thick+
                                                 self.__MainWallWidth,
                                             wallZOff-
                                                  self.__PlatformRoofThickness)),
                                    Base.Vector(1,0,0)).extrude(
                                        Base.Vector(self.__PlastructPS_97Thick,
                                                    0,0))
        bb = temp.BoundBox
        self.AddPiece(bb.YLength,bb.ZLength,"Plastruct HO Brick (PS-97)")
        windowOrigin = Base.Vector(bb.XMin,
                                   bb.YMin+self.__PlastructPS_97Thick+
                                    (self.__WindowPostWidth/2),
                                   bb.ZMin+self.__KneeWallHeight+
                                    self.__PlatformRoofThickness)
        w_y = self.__PlatformStairWidth-self.__WindowPostWidth
        temp = temp.cut(
            Part.makePlane(self.__WindowHeight,
                           w_y,
                           windowOrigin.add(Base.Vector(0,w_y,0)),
                           Base.Vector(1,0,0)).extrude(
                            Base.Vector(self.__PlastructPS_97Thick,0,0)))
        LaserCut.BricksPS_97Cut.AddCut(temp,-1,False)
        rightbridgewall = rightbridgewall.fuse(temp)
        self.outerwall = backwall.fuse(leftwall
            ).fuse(rightwall
                ).fuse(vestibleOuterWallLeft
                    ).fuse(vestibleOuterWallRight
                        ).fuse(frontwall
                            ).fuse(leftbridgewall
                                ).fuse(rightbridgewall)
        bb = self.floor.BoundBox
        LaserCut.StyreneSSS_10824Cut.AddCut(self.floor)
        self.AddPiece(bb.XLength,bb.YLength,".080 Styreen (SSS-10824)")
        innerbackwall = Part.makePlane(self.__StationHeight,
                                  self.__MainStationWidth-
                                    (2*self.__GlassWallWidth),
                                  stationOrigin.add(
                                    Base.Vector(self.__GlassWallWidth,
                                                self.__MainStationLength-
                                                    self.__MainWallWidth,
                                                self.__PlatformRoofThickness)),
                                  Base.Vector(0,1,0)
                   ).extrude(Base.Vector(0,self.__MainWallWidth,0))
        bb = innerbackwall.BoundBox
        self.AddPiece(bb.XLength,bb.ZLength,".080 Styreen (SSS-10824)")
        LaserCut.StyreneSSS_10824Cut.AddCut(innerbackwall)
        innerleftwall = Part.makePlane(self.__StationHeight,
                                  self.__MainStationLength-
                                    (2*self.__MainWallWidth),
                                  stationOrigin.add(
                                    Base.Vector(self.__GlassWallWidth,
                                                self.__MainStationLength-
                                                    self.__MainWallWidth,
                                                self.__PlatformRoofThickness)),
                                  Base.Vector(1,0,0)
                  ).extrude(Base.Vector(self.__MainWallWidth,0,0))
        bb = innerleftwall.BoundBox
        self.AddPiece(bb.YLength,bb.ZLength,".080 Styreen (SSS-10824)")
        vestibleOrigin = Base.Vector(bb.XMin,
                                     bb.YMin+
                                        ((bb.YLength-self.__VestibleWidth)/2),
                                     bb.ZMin)
        vestibleCutOrigin = vestibleOrigin.add(
            Base.Vector(0,self.__VestibleWidth-
                            self.__MainWallWidth,0))
        innerleftwall = innerleftwall.cut(
            Part.makePlane(self.__VestibleHeight,
                           self.__VestibleWidth-
                            (2*self.__MainWallWidth),
                           vestibleCutOrigin,
                           Base.Vector(1,0,0)).extrude(
                                Base.Vector(self.__MainWallWidth,0,0)))
        windowOrigin = Base.Vector(bb.XMin,
                                   bb.YMin+
                                    (self.__WindowPostWidth/2)-
                                    self.__MainWallWidth,
                                   bb.ZMin+self.__KneeWallHeight)
        yAdjust = Base.Vector(0,self.__WindowWidth,0)
        innerleftwall = innerleftwall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerleftwall = innerleftwall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__VestibleWidth+
                                          self.__WindowWidth+
                                          self.__WindowPostWidth,0))
        innerleftwall = innerleftwall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerleftwall = innerleftwall.cut(
            Part.makePlane(self.__WindowHeight,
                           self.__WindowWidth,
                           windowOrigin.add(yAdjust),
                           Base.Vector(1,0,0)).extrude(
                                    Base.Vector(self.__MainWallWidth,
                                                0,0)))
        LaserCut.StyreneSSS_10824Cut.AddCut(innerleftwall)

        innerrightwall = Part.makePlane(self.__StationHeight,
                                  self.__MainStationLength-
                                    (2*self.__MainWallWidth),
                                  stationOrigin.add(
                                    Base.Vector(self.__MainStationWidth-
                                                    self.__MainWallWidth-
                                                    self.__GlassWallWidth,
                                                self.__MainStationLength-
                                                    self.__MainWallWidth,
                                                self.__PlatformRoofThickness)),
                                  Base.Vector(1,0,0)
                  ).extrude(Base.Vector(self.__MainWallWidth,0,0))
        bb = innerrightwall.BoundBox
        self.AddPiece(bb.YLength,bb.ZLength,".080 Styreen (SSS-10824)")
        vestibleOrigin = Base.Vector(bb.XMin,
                                     bb.YMin+
                                        ((bb.YLength-self.__VestibleWidth)/2),
                                     bb.ZMin)
        vestibleCutOrigin = vestibleOrigin.add(
            Base.Vector(0,self.__VestibleWidth-
                            self.__MainWallWidth,0))
        innerrightwall = innerrightwall.cut(
            Part.makePlane(self.__VestibleHeight,
                           self.__VestibleWidth-
                            (2*self.__MainWallWidth),
                           vestibleCutOrigin,
                           Base.Vector(1,0,0)).extrude(
                                Base.Vector(self.__MainWallWidth,0,0)))
        windowOrigin = Base.Vector(bb.XMin,
                                   bb.YMin+
                                    (self.__WindowPostWidth/2)-
                                    self.__MainWallWidth,
                                   bb.ZMin+self.__KneeWallHeight)
        yAdjust = Base.Vector(0,self.__WindowWidth,0)
        innerrightwall = innerrightwall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerrightwall = innerrightwall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__VestibleWidth+
                                          self.__WindowWidth+
                                          self.__WindowPostWidth,0))
        innerrightwall = innerrightwall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerrightwall = innerrightwall.cut(
            Part.makePlane(self.__WindowHeight,
                           self.__WindowWidth,
                           windowOrigin.add(yAdjust),
                           Base.Vector(1,0,0)).extrude(
                                    Base.Vector(self.__MainWallWidth,
                                                0,0)))
        LaserCut.StyreneSSS_10824Cut.AddCut(innerrightwall)
        innerfrontwall = Part.makePlane(self.__StationHeight,
                                        self.__MainStationWidth-
                                            (2*self.__GlassWallWidth),
                                        stationOrigin.add(
                                            Base.Vector(self.__GlassWallWidth,
                                                        0,
                                                        self.__PlatformRoofThickness)),
                                        Base.Vector(0,1,0)
               ).extrude(Base.Vector(0,self.__MainWallWidth,0))
        bb = innerfrontwall.BoundBox
        self.AddPiece(bb.XLength,bb.ZLength,".080 Styreen (SSS-10824)")
        bridgePortalOrigin = Base.Vector(bb.XMin+60.32+self.__MainWallWidth,
                                         bb.YMin,
                                         bb.ZMin)
        innerfrontwall = innerfrontwall.cut(
            Part.makePlane(self.__VestibleHeight,
                           self.__BridgeWidth-
                            (2*self.__GlassWallWidth)-
                            (2*self.__MainWallWidth),
                           bridgePortalOrigin,
                           Base.Vector(0,1,0)).extrude(
                            Base.Vector(0,self.__MainWallWidth,0)))
        LaserCut.StyreneSSS_10824Cut.AddCut(innerfrontwall)

        wallLength_y = self.__CombinedTrackAndPlatformWidth#-(2*Elevator.ShaftLength)
        innerleftbridgewall = Part.makePlane(self.__StationHeight,
                                             wallLength_y,
                                             elevator2Origin.add(
                                                Base.Vector(Elevator.ShaftWidth+
                                                                self.__GlassWallWidth,
                                                            wallLength_y,
                                                            wallZOff)),
                                             Base.Vector(1,0,0)
                   ).extrude(Base.Vector(self.__MainWallWidth,0,0))
        bb = innerleftbridgewall.BoundBox
        self.AddPiece(bb.YLength,bb.ZLength,".080 Styreen (SSS-10824)")
        # windows
        windowOrigin = Base.Vector(bb.XMin,
                                   bb.YMin+self.__PlastructPS_97Thick+Elevator.ShaftLength+
                                    (self.__WindowPostWidth/2)+4.5,
                                   bb.ZMin+self.__KneeWallHeight)
        yAdjust = Base.Vector(0,self.__WindowWidth,0)
        innerleftbridgewall = innerleftbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerleftbridgewall = innerleftbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerleftbridgewall = innerleftbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerleftbridgewall = innerleftbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerleftbridgewall = innerleftbridgewall.cut(
            Part.makePlane(self.__WindowHeight,
                           self.__WindowWidth,
                           windowOrigin.add(yAdjust),
                           Base.Vector(1,0,0)).extrude(
                                    Base.Vector(self.__MainWallWidth,
                                                0,0)))
        LaserCut.StyreneSSS_10824Cut.AddCut(innerleftbridgewall)
        innerrightbridgewall = Part.makePlane(self.__StationHeight,
                                             wallLength_y,
                                             self.stairShelterOrigin2.add(
                                                Base.Vector(-(self.__MainWallWidth+
                                                              self.__GlassWallWidth),
                                                            wallLength_y-
                                                                self.__PlatformStairWidth,
                                                            wallZOff)),
                                             Base.Vector(1,0,0)
                   ).extrude(Base.Vector(self.__MainWallWidth,0,0))
        bb = innerrightbridgewall.BoundBox
        self.AddPiece(bb.YLength,bb.ZLength,".080 Styreen (SSS-10824)")
        # bridge stair doors
        doorOrigin1 = Base.Vector(bb.XMin,
                                  bb.YMin+
                                    ((self.__PlatformStairWidth-self.__SingleDoorCutWidth)/2),
                                  bb.ZMin)
        doorOrigin2 = Base.Vector(bb.XMin,
                                  bb.YMin+
                                    (bb.YLength-self.__PlatformStairWidth)+
                                    ((self.__PlatformStairWidth-self.__SingleDoorCutWidth)/2),
                                  bb.ZMin)
        self.AddPart("Tichy Train Group #8195 Single Glass Door",2)
        innerrightbridgewall = innerrightbridgewall.cut(
            self.__singleDoorCut(doorOrigin1,self.__MainWallWidth)).cut(
                self.__singleDoorCut(doorOrigin2,self.__MainWallWidth))
        # windows
        windowOrigin = Base.Vector(bb.XMin,
                                   bb.YMin+self.__PlastructPS_97Thick+Elevator.ShaftLength+
                                    (self.__WindowPostWidth/2)+4.5,
                                   bb.ZMin+self.__KneeWallHeight)
        yAdjust = Base.Vector(0,self.__WindowWidth,0)
        innerrightbridgewall = innerrightbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerrightbridgewall = innerrightbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerrightbridgewall = innerrightbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerrightbridgewall = innerrightbridgewall.cut(
            Part.makePlane(self.__WindowHeight,
                           self.__WindowWidth,
                           windowOrigin.add(yAdjust),
                           Base.Vector(1,0,0)).extrude(
                                    Base.Vector(self.__MainWallWidth,
                                                0,0)))
        windowOrigin = windowOrigin.add(
                            Base.Vector(0,self.__WindowWidth+
                                          self.__WindowPostWidth,0))
        innerrightbridgewall = innerrightbridgewall.cut(
            Part.makePlane(self.__WindowHeight,
                           self.__WindowWidth,
                           windowOrigin.add(yAdjust),
                           Base.Vector(1,0,0)).extrude(
                                    Base.Vector(self.__MainWallWidth,
                                                0,0)))
        LaserCut.StyreneSSS_10824Cut.AddCut(innerrightbridgewall)
        temp = Part.makePlane(self.__StationHeight+
                                    self.__PlatformRoofThickness,
                              self.__PlatformStairWidth-
                                self.__GlassWallWidth+
                                self.__MainWallWidth+.88,
                              self.stairShelterOrigin1.add(
                                Base.Vector(self.__TotalStairLength(
                                                self.__PlatformStairTotalRise,
                                                self.__PlatformStairWidth),
                                                    0,
                                                    wallZOff-
                                                        self.__PlatformRoofThickness
                                                    )),
                                    Base.Vector(1,0,0)).extrude(
                                        Base.Vector(self.__MainWallWidth,
                                                    0,0))
        bb = temp.BoundBox
        self.AddPiece(bb.YLength,bb.ZLength,".080 Styreen (SSS-10824)")
        windowOrigin = Base.Vector(bb.XMin,
                                   bb.YMin-self.__GlassWallWidth+
                                    (self.__WindowPostWidth/2)+.88,
                                   bb.ZMin+self.__KneeWallHeight+
                                        self.__PlatformRoofThickness)
        w_y = self.__PlatformStairWidth-self.__WindowPostWidth
        temp = temp.cut(
            Part.makePlane(self.__WindowHeight,
                           w_y,
                           windowOrigin.add(Base.Vector(0,w_y,0)),
                           Base.Vector(1,0,0)).extrude(
                            Base.Vector(self.__MainWallWidth,0,0)))
        LaserCut.StyreneSSS_10824Cut.AddCut(temp)
        stairway1innerwall = temp
        temp = Part.makePlane(self.__StationHeight+
                                self.__PlatformRoofThickness,
                              self.__TotalStairLength(
                                self.__PlatformStairTotalRise,
                                self.__PlatformStairWidth),
                              self.stairShelterOrigin1.add(
                                Base.Vector(0,
                                            -(self.__PlatformStairWidth-
                                              self.__GlassWallWidth+
                                              self.__MainWallWidth)-.88,
                                            wallZOff-
                                                self.__PlatformRoofThickness)),
                              Base.Vector(0,1,0)).extrude(
                                Base.Vector(0,self.__MainWallWidth,0))
        bb = temp.BoundBox
        self.AddPiece(bb.XLength,bb.ZLength,".080 Styreen (SSS-10824)")
        windowOrigin = Base.Vector(bb.XMin+self.__PlastructPS_97Thick+
                                    (self.__WindowPostWidth/2)+3.5,
                                   bb.YMin,
                                   bb.ZMin+self.__KneeWallHeight+
                                    self.__PlatformRoofThickness)
        temp = temp.cut(
            Part.makePlane(self.__WindowHeight,
                           self.__WindowWidth,
                           windowOrigin,
                           Base.Vector(0,1,0)).extrude(
                            Base.Vector(0,self.__MainWallWidth,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__MainWallWidth,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__MainWallWidth,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__MainWallWidth,0)))
        LaserCut.StyreneSSS_10824Cut.AddCut(innerleftwall)
        stairway1innerwall = stairway1innerwall.fuse(temp)
        temp = Part.makePlane(self.__StationHeight+
                                    self.__PlatformRoofThickness,
                              self.__PlatformStairWidth,
                              self.stairShelterOrigin2.add(
                                Base.Vector(self.__TotalStairLength(
                                                self.__PlatformStairTotalRise,
                                                self.__PlatformStairWidth),
                                                    0,
                                                    wallZOff-
                                                        self.__PlatformRoofThickness
                                                    )),
                                    Base.Vector(1,0,0)).extrude(
                                        Base.Vector(self.__MainWallWidth,
                                                    0,0))
        bb = temp.BoundBox
        self.AddPiece(bb.YLength,bb.ZLength,".080 Styreen (SSS-10824)")
        windowOrigin = Base.Vector(bb.XMin,
                                   bb.YMin+
                                    (self.__WindowPostWidth/2),
                                   bb.ZMin+self.__KneeWallHeight+
                                        self.__PlatformRoofThickness)
        w_y = self.__PlatformStairWidth-self.__WindowPostWidth
        temp = temp.cut(
            Part.makePlane(self.__WindowHeight,
                           w_y,
                           windowOrigin.add(Base.Vector(0,w_y,0)),
                           Base.Vector(1,0,0)).extrude(
                            Base.Vector(self.__MainWallWidth,0,0)))
        stairway2innerwall = temp
        LaserCut.StyreneSSS_10824Cut.AddCut(innerleftwall)
        temp = Part.makePlane(self.__StationHeight+
                                self.__PlatformRoofThickness,
                              self.__TotalStairLength(
                                self.__PlatformStairTotalRise,
                                self.__PlatformStairWidth)+
                                    self.__MainWallWidth,
                              self.stairShelterOrigin2.add(
                                Base.Vector(0,
                                            0,
                                            wallZOff-
                                                self.__PlatformRoofThickness)),
                              Base.Vector(0,1,0)).extrude(
                                Base.Vector(0,self.__MainWallWidth,0))
        bb = temp.BoundBox
        self.AddPiece(bb.XLength,bb.ZLength,".080 Styreen (SSS-10824)")
        windowOrigin = Base.Vector(bb.XMin+self.__PlastructPS_97Thick+
                                    (self.__WindowPostWidth/2)+3.5,
                                   bb.YMin,
                                   bb.ZMin+self.__KneeWallHeight+
                                    self.__PlatformRoofThickness)
        temp = temp.cut(
            Part.makePlane(self.__WindowHeight,
                           self.__WindowWidth,
                           windowOrigin,
                           Base.Vector(0,1,0)).extrude(
                            Base.Vector(0,self.__MainWallWidth,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__MainWallWidth,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__MainWallWidth,0)))
        windowOrigin = windowOrigin.add(
                        Base.Vector(self.__WindowWidth+
                                        self.__WindowPostWidth,0,0))
        temp = temp.cut(
            Part.makePlane(self.__WindowHeight,
                           self.__WindowWidth,
                           windowOrigin,#.add(xAdjust),
                           Base.Vector(0,1,0)).extrude(
                            Base.Vector(0,self.__MainWallWidth,0)))
        LaserCut.StyreneSSS_10824Cut.AddCut(temp)
        stairway2innerwall = stairway2innerwall.fuse(temp)
        self.innerwall = innerbackwall.fuse(innerleftwall
                        ).fuse(innerrightwall
                            ).fuse(innerfrontwall
                                ).fuse(innerleftbridgewall
                                    ).fuse(innerrightbridgewall
                                        ).fuse(stairway1innerwall
                                            ).fuse(stairway2innerwall)
        innerblockwall = Part.makePlane(self.__StationHeight,
                                        self.__InnerBlockWallLength,
                                        stationOrigin.add(
                                            Base.Vector(self.__InnerBlockWallXOff,
                                                        self.__InnerBlockWallYOff,
                                                        self.__PlatformRoofThickness)),
                                         Base.Vector(0,1,0)
                       ).extrude(Base.Vector(0,self.__MainWallWidth,0))
        bb = innerblockwall.BoundBox
        self.AddPiece(bb.XLength,bb.ZLength,".080 Styreen (SSS-10824)")
        innerBlockOrigin = Base.Vector(bb.XMin,bb.YMin,bb.ZMin)
        restroom1 = Part.makePlane(self.__StationHeight,
                                   self.__RestroomBackWallLength,
                                   innerBlockOrigin.add(Base.Vector(
                                        self.__RestroomBackXOff,
                                        self.__MainWallWidth+
                                            self.__RestroomBackWallLength,
                                        0)),
                                    Base.Vector(1,0,0)).extrude(
                                        Base.Vector(self.__MainWallWidth,0,0))
        bb = restroom1.BoundBox
        self.AddPiece(bb.YLength,bb.ZLength,".080 Styreen (SSS-10824)")
        LaserCut.StyreneSSS_10824Cut.AddCut(restroom1)
        rrpriv1a = Part.makePlane(self.__StationHeight,
                                 self.__RestroomPrivacyWallLength,
                                 innerBlockOrigin.add(Base.Vector(
                                    0,self.__RestroomBackWallLength+
                                        self.__MainWallWidth,0)),
                                 Base.Vector(1,0,0)).extrude(
                                    Base.Vector(self.__MainWallWidth,0,0))
        bb = rrpriv1a.BoundBox
        self.AddPiece(bb.YLength,bb.ZLength,".080 Styreen (SSS-10824)")
        LaserCut.StyreneSSS_10824Cut.AddCut(rrpriv1a)
        restroom1 = restroom1.fuse(rrpriv1a)
        rrpriv1b = Part.makePlane(self.__StationHeight,
                                  self.__RestroomPrivacyWallLength,
                                  innerBlockOrigin.add(Base.Vector(
                                    self.__RestroomPrivacyWallDX,
                                    self.__MainWallWidth+
                                        self.__RestroomPrivacyWallLength,0)),
                                  Base.Vector(1,0,0)).extrude(
                                    Base.Vector(self.__MainWallWidth,0,0))
        bb = rrpriv1b.BoundBox 
        self.AddPiece(bb.YLength,bb.ZLength,".080 Styreen (SSS-10824)")
        LaserCut.StyreneSSS_10824Cut.AddCut(rrpriv1b)
        restroom1 = restroom1.fuse(rrpriv1b)        
        restroom2 = Part.makePlane(self.__StationHeight,
                                   self.__RestroomBackWallLength,
                                   innerBlockOrigin.add(Base.Vector(
                                        self.__InnerBlockWallLength-
                                            self.__RestroomBackXOff,
                                        self.__MainWallWidth+
                                            self.__RestroomBackWallLength,
                                        0)),
                                    Base.Vector(1,0,0)).extrude(
                                        Base.Vector(-self.__MainWallWidth,0,0))
        bb = restroom2.BoundBox
        LaserCut.StyreneSSS_10824Cut.AddCut(restroom2)
        rrpriv2a = Part.makePlane(self.__StationHeight,
                                 self.__RestroomPrivacyWallLength,
                                 innerBlockOrigin.add(Base.Vector(
                                    self.__InnerBlockWallLength-
                                        self.__MainWallWidth,
                                    self.__MainWallWidth+
                                        self.__RestroomBackWallLength,0)),
                                 Base.Vector(1,0,0)).extrude(
                                    Base.Vector(self.__MainWallWidth,0,0))
        bb = rrpriv2a.BoundBox
        self.AddPiece(bb.YLength,bb.ZLength,".080 Styreen (SSS-10824)")
        LaserCut.StyreneSSS_10824Cut.AddCut(rrpriv2a)
        restroom2 = restroom2.fuse(rrpriv2a)
        rrpriv2b = Part.makePlane(self.__StationHeight,
                                  self.__RestroomPrivacyWallLength,
                                  innerBlockOrigin.add(Base.Vector(
                                    self.__InnerBlockWallLength-
                                        self.__RestroomPrivacyWallDX,
                                    self.__MainWallWidth+
                                        self.__RestroomPrivacyWallLength,0)),
                                  Base.Vector(1,0,0)).extrude(
                                    Base.Vector(-self.__MainWallWidth,0,0))
        bb = rrpriv2b.BoundBox 
        self.AddPiece(bb.YLength,bb.ZLength,".080 Styreen (SSS-10824)")
        LaserCut.StyreneSSS_10824Cut.AddCut(rrpriv2b)
        restroom2 = restroom2.fuse(rrpriv2b)
        departboardOrig = innerBlockOrigin.add(
                                Base.Vector(self.__DepartureBoardXOffset,
                                            0,
                                            self.__DepartureBoardZOffset))
        innerblockwall = innerblockwall.cut(
            Part.makePlane(self.__DepartureBoardHeight,
                           self.__DepartureBoardWidth,
                           departboardOrig,
                           Base.Vector(0,1,0)).extrude(
                            Base.Vector(0,self.__MainWallWidth,0)))
        ticketWindowOrig = innerBlockOrigin.add(
                                Base.Vector(self.__TicketCounterXOffset,
                                            0,
                                            self.__TicketCounterHeight))
        innerblockwall = innerblockwall.cut(
            Part.makePlane(self.__TicketWindowHeight,
                           self.__TicketWindowWidth,
                           ticketWindowOrig,
                           Base.Vector(0,1,0)).extrude(
                            Base.Vector(0,self.__MainWallWidth,0)))
        LaserCut.StyreneSSS_10824Cut.AddCut(innerblockwall)
        self.innerblock = innerblockwall.fuse(restroom1).fuse(restroom2)
        # ceiling
        ceil1 = Part.makePlane(self.__BridgeWidth,
                               self.__CombinedTrackAndPlatformWidth,
                               elevator2Origin.add(
                                    Base.Vector(Elevator.ShaftWidth,
                                                0,
                                                self.__PlatformRoofHeight+
                                                    self.__PlatformRoofThickness-
                                                    self.__PlatformHeight+
                                                    self.__StationHeight+
                                                    self.__PlatformRoofThickness))
                  ).extrude(Base.Vector(0,0,self.__CeilingAndRoofThickness))
        ceil2 = Part.makePlane(self.__MainStationWidth,
                                self.__MainStationLength,
                                stationOrigin.add(
                                    Base.Vector(0,0,
                                                self.__PlatformRoofThickness+
                                                    self.__StationHeight))
               ).extrude(Base.Vector(0,0,self.__CeilingAndRoofThickness))
        stair1Ceiling = Part.makePlane(self.__TotalStairLength(
                                            self.__PlatformStairTotalRise,
                                            self.__PlatformStairWidth)+
                                        self.__MainWallWidth+
                                        self.__GlassWallWidth+.12,
                                       self.__PlatformStairWidth+
                                        self.__MainWallWidth+
                                        self.__GlassWallWidth,
                                       self.stairShelterOrigin1.add(
                                        Base.Vector(0,
                                                    -(self.__PlatformStairWidth+
                                                      self.__GlassWallWidth+
                                                      self.__MainWallWidth),
                                                    wallZOff+
                                                        self.__StationHeight))
                        ).extrude(Base.Vector(0,0,self.__CeilingAndRoofThickness))
        stair2Ceiling = Part.makePlane(self.__TotalStairLength(
                                            self.__PlatformStairTotalRise,
                                            self.__PlatformStairWidth)+
                                        self.__MainWallWidth+
                                        self.__GlassWallWidth+.12,
                                       self.__PlatformStairWidth+
                                        self.__MainWallWidth+
                                        self.__GlassWallWidth,
                                       self.stairShelterOrigin2.add(
                                        Base.Vector(0,
                                                    -(self.__PlatformStairWidth),
                                                    wallZOff+
                                                        self.__StationHeight))
                        ).extrude(Base.Vector(0,0,self.__CeilingAndRoofThickness))
        self.ceiling = ceil1.fuse(ceil2).fuse(stair1Ceiling
                                ).fuse(stair2Ceiling)
        bb = self.ceiling.BoundBox
        LaserCut.StyreneSSS_10224Cut.AddCut(self.ceiling)
        self.AddPiece(bb.XLength,bb.YLength,".020 Styreen (SSS-10224)")
        # roof
        self.roof = self.ceiling.copy().translate(Base.Vector(0,0,self.__CeilingAndRoofThickness+.125*25.4))
        bb = self.roof.BoundBox
        self.AddPiece(bb.XLength,bb.YLength,".020 Styreen (SSS-10224)")
        LaserCut.StyreneSSS_10224Cut.AddCut(self.roof)
        self.vestibleRoofRight = self.vestibleCeilingRight.copy().translate(Base.Vector(0,0,.125*25.4+self.__CeilingAndRoofThickness))
        bb = self.vestibleRoofRight.BoundBox
        self.AddPiece(bb.XLength,bb.YLength,".020 Styreen (SSS-10224)")
        LaserCut.StyreneSSS_10224Cut.AddCut(self.vestibleRoofRight)
        self.vestibleRoofLeft = self.vestibleCeilingLeft.copy().translate(Base.Vector(0,0,.125*25.4+self.__CeilingAndRoofThickness))
        bb = self.vestibleRoofLeft.BoundBox
        self.AddPiece(bb.XLength,bb.YLength,".020 Styreen (SSS-10224)")
        LaserCut.StyreneSSS_10224Cut.AddCut(self.vestibleRoofLeft)
        self.AddPart("Tichy Train Group #8193 Strap Railing")
    def show(self,doc=None):
        if doc==None:
            doc = App.activeDocument()
        self.platform1Elevator.show(doc)
        self.platform2Elevator.show(doc)
        obj = doc.addObject("Part::Feature",self.name+"_Platform1Stairs")
        obj.Shape = self.platform1Stair
        obj.Label=self.name+"_Platform1Stairs"
        obj.ViewObject.ShapeColor=self.__StairsColor
        obj = doc.addObject("Part::Feature",self.name+"_Platform2Stairs")
        obj.Shape = self.platform2Stair
        obj.Label=self.name+"_Platform2Stairs"
        obj.ViewObject.ShapeColor=self.__StairsColor
        obj = doc.addObject("Part::Feature",self.name+"_Platform1")
        obj.Shape = self.platform1
        obj.Label=self.name+"_Platform1"
        obj.ViewObject.ShapeColor=self.__StairsColor
        obj = doc.addObject("Part::Feature",self.name+"_Platform2")
        obj.Shape = self.platform2
        obj.Label=self.name+"_Platform2"
        obj.ViewObject.ShapeColor=self.__StairsColor
        obj = doc.addObject("Part::Feature",self.name+"_Platform1StairShelter")
        obj.Shape = self.stair1Shelter
        obj.Label=self.name+"_Platform1StairShelter"
        obj.ViewObject.ShapeColor=(1.0,1.0,1.0)
        obj.ViewObject.Transparency=90
        obj = doc.addObject("Part::Feature",self.name+"_Platform2StairShelter")
        obj.Shape = self.stair2Shelter
        obj.Label=self.name+"_Platform2StairShelter"
        obj.ViewObject.ShapeColor=(1.0,1.0,1.0)
        obj.ViewObject.Transparency=90
        obj = doc.addObject("Part::Feature",self.name+"_Platform1ElevatorShelter")
        obj.Shape = self.elevator1Shelter
        obj.Label=self.name+"_Platform1ElevatorShelter"
        obj.ViewObject.ShapeColor=(1.0,1.0,1.0)
        obj.ViewObject.Transparency=90
        obj = doc.addObject("Part::Feature",self.name+"_Platform2ElevatorShelter")
        obj.Shape = self.elevator2Shelter
        obj.Label=self.name+"_Platform2ElevatorShelter"
        obj.ViewObject.ShapeColor=(1.0,1.0,1.0)
        obj.ViewObject.Transparency=90
        obj = doc.addObject("Part::Feature",self.name+"_StationFloor")
        obj.Shape = self.floor
        obj.Label=self.name+"_StationFloor"
        obj.ViewObject.ShapeColor=self.__FloorColor
        obj = doc.addObject("Part::Feature",self.name+"_StationWall")
        obj.Shape = self.wall
        obj.Label=self.name+"_StationWall"
        obj.ViewObject.ShapeColor=(1.0,1.0,1.0)
        obj.ViewObject.Transparency=90
        obj = doc.addObject("Part::Feature",self.name+"_BrickWall")
        obj.Shape = self.outerwall
        obj.Label=self.name+"_BrickWall"
        obj.ViewObject.ShapeColor=self.__BrickWallColor
        obj = doc.addObject("Part::Feature",self.name+"_LeftVestibleInnerWall")
        obj.Shape = self.vestibleInnerWallLeft
        obj.Label=self.name+"_LeftVestibleInnerWall"
        obj.ViewObject.ShapeColor=self.__InnerWallColor
        obj = doc.addObject("Part::Feature",self.name+"_RightVestibleInnerWall")
        obj.Shape = self.vestibleInnerWallRight
        obj.Label=self.name+"_RightVestibleInnerWall"
        obj.ViewObject.ShapeColor=self.__InnerWallColor
        obj = doc.addObject("Part::Feature",self.name+"_InnerWall")
        obj.Shape = self.innerwall
        obj.Label=self.name+"_InnerWall"
        obj.ViewObject.ShapeColor=self.__InnerWallColor
        obj = doc.addObject("Part::Feature",self.name+"_InnerBlock")
        obj.Shape = self.innerblock
        obj.Label=self.name+"_InnerBlock"
        obj.ViewObject.ShapeColor=self.__InnerWallColor
        obj = doc.addObject("Part::Feature",self.name+"_Ceiling")
        obj.Shape = self.ceiling
        obj.Label=self.name+"_Ceiling"
        obj.ViewObject.ShapeColor=self.__InnerWallColor
        obj = doc.addObject("Part::Feature",self.name+"_VestibleCeilingLeft")
        obj.Shape = self.vestibleCeilingLeft
        obj.Label=self.name+"_VestibleCeilingLeft"
        obj.ViewObject.ShapeColor=self.__InnerWallColor
        obj = doc.addObject("Part::Feature",self.name+"_VestibleCeilingRight")
        obj.Shape = self.vestibleCeilingRight
        obj.Label=self.name+"_VestibleCeilingRight"
        obj.ViewObject.ShapeColor=self.__InnerWallColor
        obj = doc.addObject("Part::Feature",self.name+"_Roof")
        obj.Shape = self.roof
        obj.Label=self.name+"_Roof"
        obj.ViewObject.ShapeColor=self.__RoofColor
        obj = doc.addObject("Part::Feature",self.name+"_VestibleRoofRight")
        obj.Shape = self.vestibleRoofRight
        obj.Label=self.name+"_VestibleRoofRight"
        obj.ViewObject.ShapeColor=self.__RoofColor
        obj = doc.addObject("Part::Feature",self.name+"_VestibleRoofLeft")
        obj.Shape = self.vestibleRoofLeft
        obj.Label=self.name+"_VestibleRoofLeft"
        obj.ViewObject.ShapeColor=self.__RoofColor
        
if __name__ == '__main__':
    if "OverStation" in App.listDocuments().keys():
        App.closeDocument("OverStation")
    doc = App.newDocument("OverStation")
    station = OverStation("Station",Base.Vector(0,0,0))
    station.show(doc)
    #App.ActiveDocument=doc
    #Gui.ActiveDocument=doc
    #Gui.activeDocument().activeView().viewTop()
    #Gui.SendMsgToActiveView("ViewFit")
    OverStation.ListParts("OverStationParts.csv")
    OverStation.ListCuts("OverStationCuts.csv")
    LaserCut.CopolysterSSC_104Cut.Flush()
    LaserCut.BricksPS_97Cut.Flush()
    LaserCut.StyreneSSS_10824Cut.Flush() 
    LaserCut.StyreneSSS_10224Cut.Flush()
