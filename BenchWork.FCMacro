#*****************************************************************************
#
#  System        : 
#  Module        : 
#  Object Name   : $RCSfile$
#  Revision      : $Revision$
#  Date          : $Date$
#  Author        : $Author$
#  Created By    : Robert Heller
#  Created       : 2026-04-17 09:09:12
#  Last Modified : <260622.0808>
#
#  Description	
#
#  Notes
#
#  History
#	
#*****************************************************************************
#
#    Copyright (C) 2026  Robert Heller D/B/A Deepwoods Software
#			51 Locke Hill Road
#			Wendell, MA 01379-9728
#
#    This program is free software; you can redistribute it and/or modify
#    it under the terms of the GNU General Public License as published by
#    the Free Software Foundation; either version 2 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program; if not, write to the Free Software
#    Foundation, Inc., 675 Mass Ave, Cambridge, MA 02139, USA.
#
# 
#
#*****************************************************************************


import FreeCAD as App
import Part, TechDraw, TechDrawGui
from FreeCAD import Base

import os
import sys
sys.path.append(os.path.dirname(__file__))
import csv
import math
import Units
from debug import debug
import datetime                                                                 

import time
from PySide.QtCore import QCoreApplication, QEventLoop, QTimer

def execute(loop, ms):
    timer = QTimer()
    timer.setSingleShot(True)
    
    timer.timeout.connect(loop.quit)
    timer.start(ms)
    loop.exec_()

def sleep(ms):
    if not QCoreApplication.instance():
        app = QCoreApplication([])
        execute(app, ms)
    else:
        loop = QEventLoop()
        execute(loop, ms)
                                        



import csv

def NormalizeMM(x):
    return round(x,3)

class BOMHelper(object):
    __BOM = dict()
    @classmethod
    def AddPiece(cls,width,height,kind):
        key = (NormalizeMM(width),NormalizeMM(height),kind)
        if key in cls.__BOM:
            cls.__BOM[key] += 1
        else:
            cls.__BOM[key] = 1
    @classmethod
    def _normPartSizeMM(cls,t):
        return ("%.3fx%.3f" % t)
    @staticmethod
    def _inch(mm):
        return mm / 25.4
    @classmethod
    def _normPartSizeIN(cls,t):
        X, Y = t
        return ("%.4fx%.4f" % (cls._inch(X), cls._inch(Y)))
    _units = 'in'
    @classmethod
    def SetUnits(cls,units):
        if units == 'in' or units == 'mm':
            cls._units = units
        else:
            raise RuntimeError("Unsupport units!")
    @classmethod
    def GetUnits(cls):
        return cls._units
    @classmethod
    def _normPartSize(cls,t):
        if cls._units == 'in':
            return cls._normPartSizeIN(t)
        elif cls._units == 'mm':
            return BOMHelper._normPartSizeMM(t)
        else:
            raise RuntimeError("Unsupport units!")
    @classmethod
    def ListCuts(cls,filename):
        keys = list(cls.__BOM.keys())
        keys.sort()
        f = open(filename,"w")
        w = csv.writer(f)
        w.writerow([("Size (%s)" % cls._units),"Count"])
        for key in keys:
            X, Y, kind = key
            w.writerow([cls._normPartSize((X,Y)),kind,cls.__BOM[key]])
        f.close()
    

class PineBoard(BOMHelper):
    __thick = Units.mm(3/4)
    def __init__(self):
        raise RuntimeError("No Instances allowed for PineBoard!")
    @classmethod
    def BoardThickness(cls):
        return cls.__thick
    __Color = (0xBA/255.0, 0x70/255.0, 0x0F/255.0)
    @classmethod
    def Color(cls):
        return cls.__Color
    @classmethod
    def ZXBoard(cls,origin,width,length):
        if not isinstance(origin,Base.Vector):
            raise RuntimeError("origin is not a Vector!")
        board = Part.makePlane(width,length,origin,Base.Vector(0,1,0)).extrude(Base.Vector(0,cls.__thick,0))
        bb = board.BoundBox
        cls.AddPiece(bb.ZLength,bb.XLength,"Pine board (3/4in)")
        return board
    @classmethod
    def YXBoard(cls,origin,width,length):
        if not isinstance(origin,Base.Vector):
            raise RuntimeError("origin is not a Vector!")
        board = Part.makePlane(width,length,origin,Base.Vector(0,0,1)).extrude(Base.Vector(0,0,cls.__thick))
        bb = board.BoundBox
        cls.AddPiece(bb.YLength,bb.XLength,"Pine board (3/4in)")
        return board
    @classmethod
    def ZYBoard(cls,origin,width,length):
        if not isinstance(origin,Base.Vector):
            raise RuntimeError("origin is not a Vector!")
        board = Part.makePlane(width,length,origin.add(Base.Vector(0,length,0)),
                               Base.Vector(1,0,0)) \
                  .extrude(Base.Vector(cls.__thick,0,0))
        bb = board.BoundBox
        cls.AddPiece(bb.ZLength,bb.YLength,"Pine board (3/4in)")
        return board
    @classmethod
    def XYBoard(cls,origin,width,length):
        if not isinstance(origin,Base.Vector):
            raise RuntimeError("origin is not a Vector!")
        board = Part.makePlane(width,length,origin,Base.Vector(0,0,1)).extrude(Base.Vector(0,0,cls.__thick))
        bb = board.BoundBox
        cls.AddPiece(bb.YLength,bb.XLength,"Pine board (3/4in)")
        return board
    @classmethod
    def ZBeam(cls,origin,length):
        if not isinstance(origin,Base.Vector):
            raise RuntimeError("origin is not a Vector!")
        beam = Part.makePlane(cls.__thick,cls.__thick,origin,Base.Vector(0,0,1)).extrude(Base.Vector(0,0,length))
        bb = beam.BoundBox
        cls.AddPiece(bb.YLength,bb.ZLength,"Pine board (3/4in)")
        return beam
    @classmethod
    def XBeam(cls,origin,length):
        if not isinstance(origin,Base.Vector):
            raise RuntimeError("origin is not a Vector!")
        beam = Part.makePlane(cls.__thick,cls.__thick,origin,Base.Vector(1,0,0)).extrude(Base.Vector(length,0,0))
        bb = beam.BoundBox
        cls.AddPiece(bb.YLength,bb.XLength,"Pine board (3/4in)")
        return beam
    @classmethod
    def YBeam(cls,origin,length):
        if not isinstance(origin,Base.Vector):
            raise RuntimeError("origin is not a Vector!")
        beam = Part.makePlane(cls.__thick,cls.__thick,origin,Base.Vector(0,1,0)).extrude(Base.Vector(0,length,0))
        bb = beam.BoundBox
        cls.AddPiece(bb.XLength,bb.YLength,"Pine board (3/4in)")
        return beam
         

class Sheet(BOMHelper):
    def __init__(self):
        raise RuntimeError("No Instances allowed for Sheet")
    __AB3_8Thick = Units.mm(11/32)
    @classmethod
    def ABThick(cls):
        return cls.__AB3_8Thick
    __Birch1_4Thick = Units.mm(7/32)
    @classmethod
    def BirchThick(cls):
        return cls.__Birch1_4Thick
    __Masonite1_8Thick = Units.mm(1/8)
    @classmethod
    def MasoniteThick(cls):
        return cls.__Masonite1_8Thick
    __Lexan1_8Thick = Units.mm(1/8)
    @classmethod
    def LexanThick(cls):
        return cls.__Lexan1_8Thick
    __Color = (1.0,1.0,0.0)
    __BirchColor = (1.0,1.0,1.0)
    __MasoniteColor = (139.0/255.0,  35.0/255.0,  35.0/255.0) 
    @classmethod
    def Color(cls):
        return cls.__Color
    @classmethod
    def BirchColor(cls):
        return cls.__BirchColor
    @classmethod
    def MasoniteColor(cls):
        return cls.__MasoniteColor
    @classmethod
    def XYSheet(cls,origin,width,length,sheettype="AB"):
        if not isinstance(origin,Base.Vector):
            raise RuntimeError("origin is not a Vector!")
        thick = None
        kind = None
        if sheettype == "AB":
            thick = cls.__AB3_8Thick
            kind = "3/8 AB Plywood"
        elif sheettype == "Birch":
            thick = cls.__Birch1_4Thick
            kind = "1/4 Birch Plywood"
        elif sheettype == "Masonite":
            thick = cls.__Masonite1_8Thick
            kind = "1/8 Masonite"
        elif sheettype == "Lexan":
            thick = cls.__Lexan1_8Thick
            kind = "1/8 Lexan"
        else:
            raise RuntimeError("Unsupport plywood type")
        sheet = Part.makePlane(width,length,origin,Base.Vector(0,0,1)).extrude(Base.Vector(0,0,thick))
        bb = sheet.BoundBox
        cls.AddPiece(bb.XLength,bb.YLength,kind)
        return sheet
    @classmethod
    def XZSheet(cls,origin,width,length,sheettype="AB"):
        if not isinstance(origin,Base.Vector):
            raise RuntimeError("origin is not a Vector!")
        thick = None
        kind = None
        if sheettype == "AB":
            thick = cls.__AB3_8Thick
            kind = "3/8 AB Plywood"
        elif sheettype == "Birch":
            thick = cls.__Birch1_4Thick
            kind = "1/4 Birch Plywood"
        elif sheettype == "Masonite":
            thick = cls.__Masonite1_8Thick
            kind = "1/8 Masonite"
        elif sheettype == "Lexan":
            thick = cls.__Lexan1_8Thick
            kind = "1/8 Lexan"
        else:
            raise RuntimeError("Unsupport plywood type")
        sheet = Part.makePlane(width,length,origin,Base.Vector(0,1,0)).extrude(Base.Vector(0,thick,0))
        bb = sheet.BoundBox
        cls.AddPiece(bb.XLength,bb.ZLength,kind)
        return sheet
    @classmethod
    def YZSheet(cls,origin,width,length,sheettype="AB"):
        if not isinstance(origin,Base.Vector):
            raise RuntimeError("origin is not a Vector!")
        thick = None
        kind = None
        if sheettype == "AB":
            thick = cls.__AB3_8Thick
            kind = "3/8 AB Plywood"
        elif sheettype == "Birch":
            thick = cls.__Birch1_4Thick
            kind = "1/4 Birch Plywood"
        elif sheettype == "Masonite":
            thick = cls.__Masonite1_8Thick
            kind = "1/8 Masonite"
        elif sheettype == "Lexan":
            thick = cls.__Lexan1_8Thick
            kind = "1/8 Lexan"
        else:
            raise RuntimeError("Unsupport plywood type")
        sheet = Part.makePlane(width,length,origin.add(Base.Vector(0,length,0)),Base.Vector(1,0,0)).extrude(Base.Vector(thick,0,0))
        bb = sheet.BoundBox
        cls.AddPiece(bb.ZLength,bb.YLength,kind)
        return sheet
    

class BaseUnit(object):
    __Length = Units.mm(Units.inches(3))
    __Depth  = Units.mm(12)
    __TotalHeight = Units.mm(12)
    @property
    def Length(self):
        return self.__Length
    @property
    def Depth(self):
        return self.__Depth;
    @property
    def TotalHeight(self):
        return self.__TotalHeight
    __BaseSupportHeight = Units.mm(5.5)
    __BaseSupportOffsets = [ Units.mm(3/8), Units.mm(11.5), Units.mm(23.5), Units.mm((Units.inches(3)-(3/8))-(3/4)) ]
    __WireHoleYCenters = [ Units.mm(3), Units.mm(6), Units.mm(9) ]
    __WireHoleZCenter  = Units.mm(5.5) / 2.0
    __WireHoleDiameter = Units.mm(2)
    __BoltHoleYCenters = [ Units.mm(1.5), Units.mm(10.5) ]
    __BoltHoleZCenters = [ Units.mm(1.5), Units.mm(4) ]
    __BoltHoleDiameter = Units.mm(1/4)
    __TunnelY1         = Units.mm(2.25)
    __TunnelY2         = Units.mm(5.75)
    __TunnelZ0         = Units.mm(5.5)+Sheet.BirchThick()
    __TunnelZTop       = Units.mm(5.5)+Sheet.BirchThick()+Units.mm(3)
    __TunnelTopRadius  = Units.mm(1/2)
    @classmethod
    def TunnelCutPattern(cls):
        panelorig = Base.Vector(0,0,0)
        panel = Sheet.YZSheet(panelorig,cls.__Depth,cls.__TotalHeight)
        bb = panel.BoundBox
        X = bb.XMin 
        XDepth = bb.XLength
        owidth = cls.__TunnelY2-cls.__TunnelY1
        oheight = cls.__TunnelZTop-cls.__TunnelZ0
        openorig = Base.Vector(X,cls.__TunnelY1+owidth,cls.__TunnelZ0)
        r1orig = openorig.add(Base.Vector(0,cls.__TunnelTopRadius,oheight-cls.__TunnelTopRadius))
        temp = Part.makePlane(cls.__TunnelTopRadius*2,
                              cls.__TunnelTopRadius*2,
                              r1orig,Base.Vector(1,0,0)).extrude(Base.Vector(XDepth,0,0))
        r1 = Part.makeCylinder(cls.__TunnelTopRadius,XDepth,
                               r1orig.add(Base.Vector(0,-cls.__TunnelTopRadius*2,0)),
                               Base.Vector(1,0,0))
        opening = opening.cut(temp.cut(r1))
        r2orig = openorig.add(Base.Vector(0,-owidth+cls.__TunnelTopRadius,
                                          oheight-cls.__TunnelTopRadius))
        temp = Part.makePlane(cls.__TunnelTopRadius*2,
                              cls.__TunnelTopRadius*2,
                              r2orig,Base.Vector(1,0,0)).extrude(Base.Vector(XDepth))
        r2 = Part.makeCylinder(cls.__TunnelTopRadius,XDepth,
                               r2orig,
                               Base.Vector(1,0,0))
        opening = opening.cut(temp.cut(r2))
        panel = panel.cut(opening)
        return panel
    def MakeTunnelCut(self,board):
        bb = board.BoundBox
        X = bb.XMin
        relX = X-self.origin.x
        XDepth = bb.XLength
        owidth = self.__TunnelY2-self.__TunnelY1
        oheight = self.__TunnelZTop-self.__TunnelZ0
        openorig = self.origin.add(Base.Vector(relX,self.__TunnelY1+owidth,
                                               self.__TunnelZ0))
        opening = Part.makePlane(oheight,owidth,
                                 openorig,
                                 Base.Vector(1,0,0)).extrude(Base.Vector(XDepth,0,0))
        r1orig = openorig.add(Base.Vector(0,self.__TunnelTopRadius,
                                          oheight-self.__TunnelTopRadius))
        temp = Part.makePlane(self.__TunnelTopRadius*2,
                              self.__TunnelTopRadius*2,
                              r1orig,Base.Vector(1,0,0)).extrude(Base.Vector(XDepth))
        r1 = Part.makeCylinder(self.__TunnelTopRadius,XDepth,
                               r1orig.add(Base.Vector(0,-self.__TunnelTopRadius*2,0)),
                               Base.Vector(1,0,0))
        opening = opening.cut(temp.cut(r1))
        r2orig = openorig.add(Base.Vector(0,-owidth+self.__TunnelTopRadius,
                                          oheight-self.__TunnelTopRadius))
        temp = Part.makePlane(self.__TunnelTopRadius*2,
                              self.__TunnelTopRadius*2,
                              r2orig,Base.Vector(1,0,0)).extrude(Base.Vector(XDepth))
        r2 = Part.makeCylinder(self.__TunnelTopRadius,XDepth,
                               r2orig,
                               Base.Vector(1,0,0))
        #self.a = temp
        #self.b = r2
        opening = opening.cut(temp.cut(r2))
        return board.cut(opening)
    @classmethod
    def WireHolesPattern(cls):
        panelorig = Base.Vector(0,0,0)
        panel = PineBoard.ZYBoard(panelorig,cls.__BaseSupportHeight,
                                  cls.__Depth)
        bb = panel.BoundBox
        X = bb.XMin 
        relX = X-panelorig.x
        XDepth = bb.XLength
        for y in cls.__WireHoleYCenters:
            hole = Part.makeCylinder(cls.__WireHoleDiameter/2,XDepth,
                                     panelorig.add(Base.Vector(relX,y,
                                                                 cls.__WireHoleZCenter)),
                                     Base.Vector(1,0,0))
            panel = panel.cut(hole)
        return panel            
    def MakeWireHoles(self,board):
        bb = board.BoundBox
        X = bb.XMin
        relX = X-self.origin.x
        XDepth = bb.XLength
        for y in self.__WireHoleYCenters:
            hole = Part.makeCylinder(self.__WireHoleDiameter/2,XDepth,
                                     self.origin.add(Base.Vector(relX,y,
                                                                 self.__WireHoleZCenter)),
                                     Base.Vector(1,0,0))
            board = board.cut(hole)
        return board
    @classmethod
    def AddBoltHolesPattern(cls,panelorig,panel):
        bb = panel.BoundBox
        X = bb.XMin 
        relX = X-panelorig.x
        XDepth = bb.XLength
        for y in cls.__BoltHoleYCenters:
            for z in cls.__BoltHoleZCenters:
                hole = Part.makeCylinder(cls.__BoltHoleDiameter/2,XDepth,
                                     panelorigin.add(Base.Vector(relX,y,z)),
                                     Base.Vector(1,0,0))
                panel = panel.cut(hole)
        return panel            
    def MakeBoltHoles(self,board):
        bb = board.BoundBox
        X = bb.XMin
        relX = X-self.origin.x
        XDepth = bb.XLength
        for y in self.__BoltHoleYCenters:
            for z in self.__BoltHoleZCenters:
                hole = Part.makeCylinder(self.__BoltHoleDiameter/2,XDepth,
                                     self.origin.add(Base.Vector(relX,y,z)),
                                     Base.Vector(1,0,0))
                board = board.cut(hole)
        return board            
    def __init__(self,name,origin):
        if not isinstance(origin,Base.Vector):
            raise RuntimeError("origin is not a Vector!")
        self.origin = origin
        self.name = name
        self.left = PineBoard.ZYBoard(
            self.origin.add(Base.Vector(self.__BaseSupportOffsets[0],0,0)),
            self.__BaseSupportHeight,
            self.__Depth)
        self.left1 = PineBoard.ZYBoard(
            self.origin.add(Base.Vector(self.__BaseSupportOffsets[1],0,0)),
            self.__BaseSupportHeight,
            self.__Depth-PineBoard.BoardThickness())
        self.right1 = PineBoard.ZYBoard(
            self.origin.add(Base.Vector(self.__BaseSupportOffsets[2],0,0)),
            self.__BaseSupportHeight,
            self.__Depth-PineBoard.BoardThickness())
        self.right = PineBoard.ZYBoard(
            self.origin.add(Base.Vector(self.__BaseSupportOffsets[3],0,0)),
            self.__BaseSupportHeight,
            self.__Depth)
        #debug("BaseUnit(): self.__BaseSupportOffsets[3] is %f",self.__BaseSupportOffsets[3])
        backlen = self.__BaseSupportOffsets[3]-self.__BaseSupportOffsets[0]
        backlen -= PineBoard.BoardThickness()
        #debug("BaseUnit(): backlen is %f",backlen)
        self.back = PineBoard.ZXBoard(
            self.origin.add(Base.Vector(PineBoard.BoardThickness()+self.__BaseSupportOffsets[0],
                                        self.__Depth-PineBoard.BoardThickness(),
                                        0)),
            self.__BaseSupportHeight,
            backlen)
        self.leftsheet = Sheet.YZSheet(self.origin,self.__Depth,self.__TotalHeight)
        self.rightsheet = Sheet.YZSheet(self.origin.add(Base.Vector(self.__Length-Sheet.ABThick(),0,0)),
                                          self.__Depth,self.__TotalHeight)
        self.backsheet = Sheet.XZSheet(self.origin.add(Base.Vector(0,self.__Depth,0)),
                                         self.__TotalHeight,self.__Length)
        self.layoutsheet = Sheet.XYSheet(self.origin.add(Base.Vector(Units.mm(3/8),
                                                                       0,
                                                                       self.__BaseSupportHeight)),
                                           self.__Length-(2*Sheet.ABThick()),
                                           self.__Depth,
                                           "Birch")
        self.bottom = Sheet.XYSheet(self.origin.add(Base.Vector(0,0,
                                                                  -Sheet.ABThick())),
                                      self.__Length,
                                      self.__Depth+Sheet.ABThick())
        self.top = Sheet.XYSheet(self.origin.add(Base.Vector(0,
                                                               Units.mm(2),
                                                               self.__TotalHeight)),
                                   self.__Length,
                                   self.__Depth-Units.mm(2)+Sheet.ABThick())
        self.leftbackdrop = Sheet.YZSheet(self.origin.add(Base.Vector(Sheet.ABThick(),
                                                                        0,
                                                                        self.__BaseSupportHeight+Sheet.BirchThick())),
                                            self.__TotalHeight-(self.__BaseSupportHeight+Sheet.BirchThick()),
                                            self.__Depth,
                                            "Masonite")
        self.rightbackdrop = Sheet.YZSheet(self.origin.add(Base.Vector(self.__Length-Sheet.ABThick()-Sheet.MasoniteThick(),
                                                                        0,
                                                                        self.__BaseSupportHeight+Sheet.BirchThick())),
                                            self.__TotalHeight-(self.__BaseSupportHeight+Sheet.BirchThick()),
                                            self.__Depth,
                                            "Masonite")
        self.backbackdrop = Sheet.XZSheet(self.origin.add(Base.Vector(Sheet.ABThick()+Sheet.MasoniteThick(),
                                                                        self.__Depth-Sheet.MasoniteThick(),
                                                                        self.__BaseSupportHeight+Sheet.BirchThick())),
                                            self.__TotalHeight-self.__BaseSupportHeight-Sheet.BirchThick(),
                                            self.__Length-(2*(Sheet.ABThick()+Sheet.MasoniteThick())),
                                            "Masonite")
        self.p1 = PineBoard.ZBeam(
                        self.origin.add(
                            Base.Vector(
                                Sheet.ABThick()+Sheet.MasoniteThick(),
                                0,
                                self.__BaseSupportHeight+Sheet.BirchThick())),
                        self.__TotalHeight-self.__BaseSupportHeight-Sheet.BirchThick())
        self.p2 = PineBoard.ZBeam(
                        self.origin.add(
                            Base.Vector(
                                Sheet.ABThick()+Sheet.MasoniteThick(),
                                self.__Depth-PineBoard.BoardThickness()-Sheet.MasoniteThick(),
                                self.__BaseSupportHeight+Sheet.BirchThick())),
                        self.__TotalHeight-self.__BaseSupportHeight-Sheet.BirchThick())
        self.p3 = PineBoard.ZBeam(
                        self.origin.add(
                            Base.Vector(
                                self.__Length-(Sheet.ABThick()+
                                               Sheet.MasoniteThick()+
                                               PineBoard.BoardThickness()),
                                0,
                                self.__BaseSupportHeight+Sheet.BirchThick())),
                        self.__TotalHeight-self.__BaseSupportHeight-Sheet.BirchThick())
        self.p4 = PineBoard.ZBeam(
                        self.origin.add(
                            Base.Vector(
                                self.__Length-(Sheet.ABThick()+
                                               Sheet.MasoniteThick()+
                                               PineBoard.BoardThickness()),
                                self.__Depth-PineBoard.BoardThickness()-Sheet.MasoniteThick(),
                                self.__BaseSupportHeight+Sheet.BirchThick())),
                        self.__TotalHeight-self.__BaseSupportHeight-Sheet.BirchThick())
        self.l1 = PineBoard.YBeam(
                    self.origin.add(
                        Base.Vector(Sheet.ABThick()+Sheet.MasoniteThick(),
                                    PineBoard.BoardThickness(),
                                    self.__TotalHeight-PineBoard.BoardThickness())),
                    self.__Depth-(2*PineBoard.BoardThickness())-Sheet.MasoniteThick())
        self.l2 = PineBoard.YBeam(
                    self.origin.add(
                        Base.Vector(self.__Length-(Sheet.ABThick()+
                                               Sheet.MasoniteThick()+
                                               PineBoard.BoardThickness()),
                                    PineBoard.BoardThickness(),
                                    self.__TotalHeight-PineBoard.BoardThickness())),
                    self.__Depth-(2*PineBoard.BoardThickness())-Sheet.MasoniteThick())
        self.l3 = PineBoard.XBeam(
                    self.origin.add(
                        Base.Vector(Sheet.ABThick()+Sheet.MasoniteThick()+
                                    PineBoard.BoardThickness(),
                                    self.__Depth-Sheet.MasoniteThick(),
                                    self.__TotalHeight-PineBoard.BoardThickness())),
                     self.__Length-(2*(Sheet.ABThick()+
                                       Sheet.MasoniteThick()+
                                       PineBoard.BoardThickness())))
        self.frontsheet = Sheet.XZSheet(
                    self.origin.add(Base.Vector(0,
                                                -Sheet.LexanThick(),
                                                -Sheet.ABThick())),
                    self.__TotalHeight-PineBoard.BoardThickness()+
                        Sheet.ABThick(),
                    self.__Length,
                    "Lexan")
        self.frontcover = Sheet.XZSheet(
                    self.origin.add(Base.Vector(0,
                                                -(Sheet.LexanThick()+
                                                  Sheet.ABThick()),
                                                -Sheet.ABThick())),
                    self.__TotalHeight+Sheet.ABThick(),
                    self.__Length)
        self.frontfillstrip = Sheet.XZSheet(
                    self.origin.add(Base.Vector(0,
                                                -Sheet.MasoniteThick(),
                                                self.__TotalHeight-
                                                    PineBoard.BoardThickness())),
                    PineBoard.BoardThickness(),
                    self.__Length,
                    "Masonite")
        self.coverblock = PineBoard.XYBoard(
                            self.origin.add(Base.Vector(
                                Sheet.ABThick()+Sheet.MasoniteThick()+
                                    PineBoard.BoardThickness(),
                                0,
                                self.__TotalHeight-PineBoard.BoardThickness())),
                            self.__Length-(2*(Sheet.ABThick()+
                                              Sheet.MasoniteThick()+
                                              PineBoard.BoardThickness())),
                            Units.mm(2))
        self.covertop = Sheet.XYSheet(
                        self.origin.add(Base.Vector(0,
                                        -(Sheet.LexanThick()+           
                                          Sheet.ABThick()),
                                        self.__TotalHeight)),
                        self.__Length,
                        Units.mm(2)+Sheet.LexanThick()+Sheet.ABThick())
        self.left1 = self.MakeWireHoles(self.left1)
        self.right1 = self.MakeWireHoles(self.right1)
    def show(self,doc=None):
        if doc==None:
            doc = App.activeDocument()
        obj = doc.addObject("Part::Feature",self.name+"_left")
        obj.Shape = self.left
        obj.Label=self.name+"_left"
        obj.ViewObject.ShapeColor=PineBoard.Color()
        obj = doc.addObject("Part::Feature",self.name+"_left1")
        obj.Shape = self.left1
        obj.Label=self.name+"_left1"
        obj.ViewObject.ShapeColor=PineBoard.Color()
        obj = doc.addObject("Part::Feature",self.name+"_right1")
        obj.Shape = self.right1
        obj.Label=self.name+"_right1"
        obj.ViewObject.ShapeColor=PineBoard.Color()
        obj = doc.addObject("Part::Feature",self.name+"_right")
        obj.Shape = self.right
        obj.Label=self.name+"_right"
        obj.ViewObject.ShapeColor=PineBoard.Color()
        obj = doc.addObject("Part::Feature",self.name+"_back")
        obj.Shape = self.back
        obj.Label=self.name+"_back"
        obj.ViewObject.ShapeColor=PineBoard.Color()
        obj = doc.addObject("Part::Feature",self.name+"_leftsheet")
        obj.Shape = self.leftsheet
        obj.Label=self.name+"_leftsheet"
        obj.ViewObject.ShapeColor=Sheet.Color()
        obj = doc.addObject("Part::Feature",self.name+"_rightsheet")
        obj.Shape = self.rightsheet
        obj.Label=self.name+"_rightsheet"
        obj.ViewObject.ShapeColor=Sheet.Color()
        obj = doc.addObject("Part::Feature",self.name+"_backsheet")
        obj.Shape = self.backsheet
        obj.Label=self.name+"_backsheet"
        obj.ViewObject.ShapeColor=Sheet.Color()
        obj = doc.addObject("Part::Feature",self.name+"_layoutsheet")
        obj.Shape = self.layoutsheet
        obj.Label=self.name+"_layoutsheet"
        obj.ViewObject.ShapeColor=Sheet.BirchColor()
        obj = doc.addObject("Part::Feature",self.name+"_bottom")
        obj.Shape = self.bottom
        obj.Label=self.name+"_bottom"
        obj.ViewObject.ShapeColor=Sheet.Color()
        obj = doc.addObject("Part::Feature",self.name+"_top")
        obj.Shape = self.top
        obj.Label=self.name+"_top"
        obj.ViewObject.ShapeColor=Sheet.Color()
        obj = doc.addObject("Part::Feature",self.name+"_leftbackdrop")
        obj.Shape = self.leftbackdrop
        obj.Label=self.name+"_leftbackdrop"
        obj.ViewObject.ShapeColor=Sheet.MasoniteColor()
        obj = doc.addObject("Part::Feature",self.name+"_rightbackdrop")
        obj.Shape = self.rightbackdrop
        obj.Label=self.name+"_rightbackdrop"
        obj.ViewObject.ShapeColor=Sheet.MasoniteColor()
        obj = doc.addObject("Part::Feature",self.name+"_backbackdrop")
        obj.Shape = self.backbackdrop
        obj.Label=self.name+"_backbackdrop"
        obj.ViewObject.ShapeColor=Sheet.MasoniteColor()
        obj = doc.addObject("Part::Feature",self.name+"_p1")
        obj.Shape = self.p1
        obj.Label=self.name+"_p1"
        obj.ViewObject.ShapeColor=PineBoard.Color()
        obj = doc.addObject("Part::Feature",self.name+"_p2")
        obj.Shape = self.p2
        obj.Label=self.name+"_p2"
        obj.ViewObject.ShapeColor=PineBoard.Color()
        obj = doc.addObject("Part::Feature",self.name+"_p3")
        obj.Shape = self.p3
        obj.Label=self.name+"_p3"
        obj.ViewObject.ShapeColor=PineBoard.Color()
        obj = doc.addObject("Part::Feature",self.name+"_p4")
        obj.Shape = self.p4
        obj.Label=self.name+"_p4"
        obj.ViewObject.ShapeColor=PineBoard.Color()
        obj = doc.addObject("Part::Feature",self.name+"_l1")
        obj.Shape = self.l1
        obj.Label=self.name+"_l1"
        obj.ViewObject.ShapeColor=PineBoard.Color()
        obj = doc.addObject("Part::Feature",self.name+"_l2")
        obj.Shape = self.l2
        obj.Label=self.name+"_l2"
        obj.ViewObject.ShapeColor=PineBoard.Color()
        obj = doc.addObject("Part::Feature",self.name+"_l3")
        obj.Shape = self.l3
        obj.Label=self.name+"_l3"
        obj.ViewObject.ShapeColor=PineBoard.Color()
        obj = doc.addObject("Part::Feature",self.name+"_frontsheet")
        obj.Shape = self.frontsheet
        obj.Label=self.name+"_frontsheet"
        obj.ViewObject.Transparency=100
        obj = doc.addObject("Part::Feature",self.name+"_frontcover")
        obj.Shape = self.frontcover
        obj.Label=self.name+"_frontcover"
        obj.ViewObject.ShapeColor=Sheet.Color()
        obj = doc.addObject("Part::Feature",self.name+"_frontfillstrip")
        obj.Shape = self.frontfillstrip
        obj.Label=self.name+"_frontfillstrip"
        obj.ViewObject.ShapeColor=Sheet.MasoniteColor()
        obj = doc.addObject("Part::Feature",self.name+"_coverblock")
        obj.Shape = self.coverblock
        obj.Label=self.name+"_coverblock"
        obj.ViewObject.ShapeColor=PineBoard.Color()
        obj = doc.addObject("Part::Feature",self.name+"_covertop")
        obj.Shape = self.covertop
        obj.Label=self.name+"_covertop"
        obj.ViewObject.ShapeColor=Sheet.Color()
        
class RightUnit(BaseUnit):
    def __init__(self,name,origin):
        super().__init__(name,origin)
        self.left = self.MakeWireHoles(self.left)
        self.leftsheet = self.MakeWireHoles(self.leftsheet)
        self.left = self.MakeBoltHoles(self.left)
        self.leftsheet = self.MakeBoltHoles(self.leftsheet)
        self.leftsheet = self.MakeTunnelCut(self.leftsheet)
        self.leftbackdrop = self.MakeTunnelCut(self.leftbackdrop)
        self.leftcover = Sheet.YZSheet(self.origin.add(Base.Vector(
                                            -Sheet.ABThick(),
                                            -(Sheet.LexanThick()+
                                              Sheet.ABThick()),
                                            -Sheet.ABThick())),
                                       self.TotalHeight+(2*Sheet.ABThick()),
                                       self.Depth+
                                        Sheet.LexanThick()+
                                        (2*Sheet.ABThick()))
    def show(self,doc=None):
        if doc==None:
            doc = App.activeDocument()
        super().show(doc)
        obj = doc.addObject("Part::Feature",self.name+"_leftcover")
        obj.Shape = self.leftcover
        obj.Label=self.name+"_leftcover"
        obj.ViewObject.ShapeColor=Sheet.Color()
        
class CenterUnit(BaseUnit):
    def __init__(self,name,origin):
        super().__init__(name,origin)
        self.left = self.MakeWireHoles(self.left)
        self.leftsheet = self.MakeWireHoles(self.leftsheet)
        self.left = self.MakeBoltHoles(self.left)
        self.leftsheet = self.MakeBoltHoles(self.leftsheet)
        self.leftsheet = self.MakeTunnelCut(self.leftsheet)
        self.leftbackdrop = self.MakeTunnelCut(self.leftbackdrop)
        self.leftcover = Sheet.YZSheet(self.origin.add(Base.Vector(
                                            -Sheet.ABThick(),
                                            -(Sheet.LexanThick()+
                                              Sheet.ABThick()),
                                            -Sheet.ABThick())),
                                       self.TotalHeight+(2*Sheet.ABThick()),
                                       self.Depth+
                                        Sheet.LexanThick()+
                                        (2*Sheet.ABThick()))
        self.right = self.MakeWireHoles(self.right)
        self.rightsheet = self.MakeWireHoles(self.rightsheet)
        self.right = self.MakeBoltHoles(self.right)
        self.rightsheet = self.MakeBoltHoles(self.rightsheet)
        self.rightsheet = self.MakeTunnelCut(self.rightsheet)
        self.rightbackdrop = self.MakeTunnelCut(self.rightbackdrop)
        self.rightcover = Sheet.YZSheet(self.origin.add(Base.Vector(
                                            self.Length,
                                            -(Sheet.LexanThick()+
                                              Sheet.ABThick()),
                                            -Sheet.ABThick())),
                                       self.TotalHeight+(2*Sheet.ABThick()),
                                       self.Depth+
                                        Sheet.LexanThick()+
                                        (2*Sheet.ABThick()))
    def show(self,doc=None):
        if doc==None:
            doc = App.activeDocument()
        super().show(doc)
        obj = doc.addObject("Part::Feature",self.name+"_leftcover")
        obj.Shape = self.leftcover
        obj.Label=self.name+"_leftcover"
        obj.ViewObject.ShapeColor=Sheet.Color()
        obj = doc.addObject("Part::Feature",self.name+"_rightcover")
        obj.Shape = self.rightcover
        obj.Label=self.name+"_rightcover"
        obj.ViewObject.ShapeColor=Sheet.Color()
        
class LeftUnit(BaseUnit):
    def __init__(self,name,origin):
        super().__init__(name,origin)
        self.right = self.MakeWireHoles(self.right)
        self.rightsheet = self.MakeWireHoles(self.rightsheet)
        self.right = self.MakeBoltHoles(self.right)
        self.rightsheet = self.MakeBoltHoles(self.rightsheet)
        self.rightsheet = self.MakeTunnelCut(self.rightsheet)
        self.rightbackdrop = self.MakeTunnelCut(self.rightbackdrop)
        self.rightcover = Sheet.YZSheet(self.origin.add(Base.Vector(
                                            self.Length,
                                            -(Sheet.LexanThick()+
                                              Sheet.ABThick()),
                                            -Sheet.ABThick())),
                                       self.TotalHeight+(2*Sheet.ABThick()),
                                       self.Depth+
                                        Sheet.LexanThick()+
                                        (2*Sheet.ABThick()))
    def show(self,doc=None):
        if doc==None:
            doc = App.activeDocument()
        super().show(doc)
        obj = doc.addObject("Part::Feature",self.name+"_rightcover")
        obj.Shape = self.rightcover
        obj.Label=self.name+"_rightcover"
        obj.ViewObject.ShapeColor=Sheet.Color()
        
if __name__ == '__main__':
    if "BenchWork" in App.listDocuments().keys():
        App.closeDocument("BenchWork")
    doc = App.newDocument("BenchWork")
    doc = App.activeDocument()
    station1 = RightUnit("RightUnit",Base.Vector(Units.mm(Units.inches(8)),0,0))
    station1.show(doc)
    center = CenterUnit("CenterUnit",Base.Vector(Units.mm(Units.inches(4)),0,0))
    center.show(doc)
    station2 = LeftUnit("LeftUnit",Base.Vector(0,0,0))
    station2.show(doc)
    Gui.activeDocument().activeView().viewTop()
    Gui.SendMsgToActiveView("ViewFit")
    BOMHelper.ListCuts("BOM.csv")
    #
    for g in doc.findObjects('TechDraw::DrawSVGTemplate'):
        doc.removeObject(g.Name)
    for g in doc.findObjects('TechDraw::DrawPage'):
        doc.removeObject(g.Name)
    for g in doc.findObjects('Spreadsheet::Sheet'):
        doc.removeObject(g.Name)
    for g in doc.findObjects('TechDraw::DrawViewPart'):
        doc.removeObject(g.Name)
    for g in doc.findObjects('TechDraw::DrawViewDimension'):
        doc.removeObject(g.Name)
    template = doc.addObject('TechDraw::DrawSVGTemplate','USLetterTemplate')
    template.Template = App.getResourceDir()+"Mod/TechDraw/Templates/USLetter_Landscape.svg"
    edt = template.EditableTexts
    edt['CompanyName'] = "Deepwoods Software"
    edt['CompanyAddress'] = '51 Locke Hill Road, Wendell, MA 01379 USA'   
    edt['DrawingTitle1']= 'Show Demo (Two station push-pull)'
    edt['DrawingTitle3']= ""
    edt['DrawnBy'] = "Robert Heller"
    edt['CheckedBy'] = ""
    edt['Approved1'] = ""
    edt['Approved2'] = ""
    edt['Code'] = ""
    edt['Weight'] = ''
    edt['DrawingNumber'] = datetime.datetime.now().ctime()
    edt['Revision'] = "A"
    template.EditableTexts = edt
    #*****
    # General wire holes (Inner supports)
    #
    page = doc.addObject('TechDraw::DrawPage','WireHolesDrillSheetPage')
    page.Template = template
    edt = page.Template.EditableTexts
    edt['DrawingTitle2']= "Wire Holes"
    edt['scale'] = 'Scale: .5'
    edt['Sheet'] = "Sheet 1 of 3"
    page.Template.EditableTexts = edt
    page.ViewObject.show()
    view = doc.addObject('TechDraw::DrawViewPart','WireHolesDrill')
    page.addView(view)
    view.Source = doc.getObject("RightUnit_left1")
    view.Direction=(1.0,0,0)
    view.ScaleType='Custom'
    view.Scale = 1/2
    view.X = 140
    view.Y = 120
    #
    # Vertex1 origin
    # Vertex12 h1 center
    # Vertex9  h2 center
    # Vertex6  h3 center
    # Edge6    h1 circumfrence
    #
    dim1 = doc.addObject('TechDraw::DrawViewDimension','H1X')
    dim1.Type = 'DistanceX'
    dim1.References2D = [ (view, 'Vertex1'), (view, 'Vertex12') ]
    dim1.FormatSpec='3in'
    dim1.Arbitrary = True
    dim1.X = -53
    dim1.Y = -8
    page.addView(dim1)
    dim2 = doc.addObject('TechDraw::DrawViewDimension','H2X')
    dim2.Type = 'DistanceX'
    dim2.References2D = [ (view, 'Vertex1'), (view, 'Vertex9') ]
    dim2.FormatSpec='6in'
    dim2.Arbitrary = True
    dim2.X = -15
    dim2.Y = -15
    page.addView(dim2)
    dim3 = doc.addObject('TechDraw::DrawViewDimension','H3X')
    dim3.Type = 'DistanceX'
    dim3.References2D = [ (view, 'Vertex1'), (view, 'Vertex6') ]
    dim3.FormatSpec='9in'
    dim3.Arbitrary = True
    dim3.X = 25
    dim3.Y = -20
    page.addView(dim3)
    dim4 = doc.addObject('TechDraw::DrawViewDimension','V1Y')
    dim4.Type = 'DistanceY'
    dim4.References2D = [ (view, 'Vertex1'), (view, 'Vertex6') ]
    dim4.FormatSpec="%.3fin"%(5.5/2)
    dim4.Arbitrary = True
    dim4.X = -72
    dim4.Y =  15
    page.addView(dim4)
    dim5 = doc.addObject('TechDraw::DrawViewDimension','D1')
    dim5.Type = 'Diameter'
    dim5.References2D = [ (view, 'Edge6') ]
    dim5.FormatSpec="2in (3x)"
    dim5.Arbitrary = True
    dim5.X = -14
    dim5.Y =  23
    page.addView(dim5)
    
    doc.recompute()
    sleep(500)
    TechDrawGui.exportPageAsPdf(page,"WireHolesDrillSheetPage.pdf")
    #*****
    # Endplates wire and bolt holes
    #
    page = doc.addObject('TechDraw::DrawPage','EndPlateHolesDrillSheetPage')
    page.Template = template
    edt = page.Template.EditableTexts
    edt['DrawingTitle2']= "Endplates wire and bolt Holes"
    edt['scale'] = 'Scale: .5'
    edt['Sheet'] = "Sheet 2 of 3"
    page.Template.EditableTexts = edt
    page.ViewObject.show()
    view = doc.addObject('TechDraw::DrawViewPart','WireHolesDrill')
    page.addView(view)
    view.Source = doc.getObject("RightUnit_left")
    view.Direction=(1.0,0,0)
    view.ScaleType='Custom'
    view.Scale = 1/2
    view.X = 140
    view.Y = 120
    #
    # Vertex1 origin
    # Wire Holes (same as inner)
    # Vertex21 h1 center
    # Vertex18 h2 center
    # Vertex9  h3 center
    # Edge9    h1 circumfrence
    #
    dim1 = doc.addObject('TechDraw::DrawViewDimension','H1X')
    dim1.Type = 'DistanceX'
    dim1.References2D = [ (view, 'Vertex1'), (view, 'Vertex21') ]
    dim1.FormatSpec='3in'
    dim1.Arbitrary = True
    dim1.X = -46
    dim1.Y = -11
    page.addView(dim1)
    dim2 = doc.addObject('TechDraw::DrawViewDimension','H2X')
    dim2.Type = 'DistanceX'
    dim2.References2D = [ (view, 'Vertex1'), (view, 'Vertex18') ]
    dim2.FormatSpec='6in'
    dim2.Arbitrary = True
    dim2.X = -15
    dim2.Y = -15
    page.addView(dim2)
    dim3 = doc.addObject('TechDraw::DrawViewDimension','H3X')
    dim3.Type = 'DistanceX'
    dim3.References2D = [ (view, 'Vertex1'), (view, 'Vertex9') ]
    dim3.FormatSpec='9in'
    dim3.Arbitrary = True
    dim3.X = 25
    dim3.Y = -20
    page.addView(dim3)
    dim4 = doc.addObject('TechDraw::DrawViewDimension','V1Y')
    dim4.Type = 'DistanceY'
    dim4.References2D = [ (view, 'Vertex1'), (view, 'Vertex9') ]
    dim4.FormatSpec="%.3fin"%(5.5/2)
    dim4.Arbitrary = True
    dim4.X = -72
    dim4.Y =  15
    page.addView(dim4)
    dim5 = doc.addObject('TechDraw::DrawViewDimension','D1')
    dim5.Type = 'Diameter'
    dim5.References2D = [ (view, 'Edge9') ]
    dim5.FormatSpec="2in (3x)"
    dim5.Arbitrary = True
    dim5.X = -14
    dim5.Y =  23
    page.addView(dim5)
    # Bolt holes
    # Vertex15 b1 center
    # Vertex24 b2 center
    # Vertex12 b3 center
    # Vertex6  b4 center
    # Edge6    b3 circumfrence
    dim6 = doc.addObject('TechDraw::DrawViewDimension','BH1X')
    dim6.Type = 'DistanceX'
    dim6.References2D = [ (view, 'Vertex1'), (view, 'Vertex24') ]
    dim6.FormatSpec='1.5in'
    dim6.Arbitrary = True 
    dim6.X = -66
    dim6.Y = -51
    page.addView(dim6) 
    dim7 = doc.addObject('TechDraw::DrawViewDimension','BH2X')
    dim7.Type = 'DistanceX'
    dim7.References2D = [ (view, 'Vertex1'), (view, 'Vertex12') ]
    dim7.FormatSpec='10.5in'
    dim7.Arbitrary = True 
    dim7.X =  44
    dim7.Y = -37
    page.addView(dim7) 

    dim8 = doc.addObject('TechDraw::DrawViewDimension','BH1Y')
    dim8.Type = 'DistanceY'
    dim8.References2D = [ (view, 'Vertex1'), (view, 'Vertex6') ]
    dim8.FormatSpec='1.5in'
    dim8.Arbitrary = True 
    dim8.X = -94
    dim8.Y = -25
    page.addView(dim8) 
    dim9 = doc.addObject('TechDraw::DrawViewDimension','BH2Y')
    dim9.Type = 'DistanceY'
    dim9.References2D = [ (view, 'Vertex1'), (view, 'Vertex12') ]
    dim9.FormatSpec='4in'
    dim9.Arbitrary = True 
    dim9.X = -107
    dim9.Y =   -4
    page.addView(dim9) 

    dim10 = doc.addObject('TechDraw::DrawViewDimension','BD1')
    dim10.Type = 'Diameter'
    dim10.References2D = [ (view, 'Edge6') ]
    dim10.FormatSpec=".25in (4x)"
    dim10.Arbitrary = True
    dim10.X =  93
    dim10.Y =  26
    page.addView(dim10)

    doc.recompute()
    sleep(500)
    TechDrawGui.exportPageAsPdf(page,"EndPlateHolesDrillSheetPage.pdf")
    #****
    # Endplates tunnel cutout
    #
    page = doc.addObject('TechDraw::DrawPage','EndPlateTunnelCutOut')
    page.Template = template
    edt = page.Template.EditableTexts
    edt['DrawingTitle2']= "Endplates Tunnel cutout"
    edt['scale'] = 'Scale: .25'
    edt['Sheet'] = "Sheet 3 of 3"
    page.Template.EditableTexts = edt
    page.ViewObject.show()
    view = doc.addObject('TechDraw::DrawViewPart','EndPlateTunnelCutOut')
    page.addView(view)
    view.Source = doc.getObject("RightUnit_leftsheet")
    view.Direction=(1.0,0,0)
    view.ScaleType='Custom'
    view.Scale = 1/4
    view.X = 140
    view.Y = 120
    #
    # Vertex1 origin
    # Vertex32 A
    # Vertex30 B
    # Edge14   Curve 1
    # Vertex31 Curve 1 center
    # Vertex29 C
    # Vertex27 D
    # Edge12   Curve 2
    # Vertex28 Curve 2 center
    # Vertex26 E
    # Vertex25 F
    #
    dim1 = doc.addObject('TechDraw::DrawViewDimension','H1X')
    dim1.Type = 'DistanceX'
    dim1.References2D = [ (view, 'Vertex1'), (view, 'Vertex32') ]
    dim1.FormatSpec='2.25in'
    dim1.Arbitrary = True
    dim1.X = -50
    dim1.Y =  39
    page.addView(dim1)
    dim2 = doc.addObject('TechDraw::DrawViewDimension','H2X')
    dim2.Type = 'DistanceX'
    dim2.References2D = [ (view, 'Vertex1'), (view, 'Vertex25') ]
    dim2.FormatSpec='5.75in'
    dim2.Arbitrary = True
    dim2.X = -20
    dim2.Y =  59
    page.addView(dim2)
    dim3 = doc.addObject('TechDraw::DrawViewDimension','H1Y')
    dim3.Type = 'DistanceY'
    dim3.References2D = [ (view, 'Vertex1'), (view, 'Vertex32') ]
    dim3.FormatSpec='5.75in'
    dim3.Arbitrary = True
    dim3.X = -54
    dim3.Y = -10
    page.addView(dim3)
    dim4 = doc.addObject('TechDraw::DrawViewDimension','H2Y')
    dim4.Type = 'DistanceY'
    dim4.References2D = [ (view, 'Vertex1'), (view, 'Vertex29') ]
    dim4.FormatSpec='8.75in'
    dim4.Arbitrary = True
    dim4.X = -66
    dim4.Y =  10
    page.addView(dim4)
    dim5 = doc.addObject('TechDraw::DrawViewDimension','Rad1')
    dim5.Type = 'Radius'
    dim5.References2D = [ (view, 'Edge12') ]
    dim5.FormatSpec='.5in radius (2x)'
    dim5.Arbitrary = True
    dim5.X =  14
    dim5.Y =  45
    page.addView(dim5)
    
    doc.recompute()
    sleep(500)
    TechDrawGui.exportPageAsPdf(page,"EndPlateTunnelCutOutPage.pdf")
